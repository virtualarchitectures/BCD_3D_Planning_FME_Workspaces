FME workspace BCD_3D_Model_Layers.fmw

Parameters:
- SourceDataset_ESRISHAPE = C:\Users\odawkins\Dropbox\Building_City_Dashboards\Data\2019_06_19_BCD_3D_Data_Layers_REVISED\DCC_Development_Planning_Dublinked\dccdevelopmentplanp20141002-1159.shp   # Source Esri Shapefile(s)
- DestDataset_FBX = C:\Users\odawkins\Desktop\DevPlan   # Destination FBX Folder
- DestDataset_CSV2 = C:\Users\odawkins\Desktop\DevPlan   # Destination CSV (Comma Separated Value) Folder
- SourceDataset_CSV2 = C:\Users\odawkins\Dropbox\Building_City_Dashboards\Data\2019_06_19_BCD_3D_Data_Layers_REVISED\DCC_Development_Planning_Dublinked\dublincityplanzonesgztp20141016-1441_CLEANED.csv   # Source CSV (Comma Separated Value) File(s)
- SourceDataset_ESRISHAPE_15 = C:\Users\odawkins\Dropbox\Building_City_Dashboards\Data\2019_06_19_BCD_3D_Data_Layers_REVISED\D3D_Central_Dublin_Model_Boundary\BCD_Boundary.shp   # Source Esri Shapefile(s)
- SourceDataset_ESRISHAPE_13 = C:\Users\odawkins\Dropbox\Building_City_Dashboards\Data\2019_06_19_BCD_3D_Data_Layers_REVISED\DCC_Planning_Applications_Dublinked\DCC_PlanAppsREPROJECTED.shp   # Source Esri Shapefile(s)
- DestDataset_FBX_9 = C:\Users\odawkins\Desktop\PlanningApps   # Destination FBX Folder
- SourceDataset_ESRISHAPE_11 = C:\Users\odawkins\Dropbox\Building_City_Dashboards\Data\2019_06_19_BCD_3D_Data_Layers_REVISED\Small_Areas_Population_Statistics_CSO\Small_Areas__Generalised_20m__OSi_National_Boundaries\Small_Areas__Generalised_20m__OSi_National_Boundaries.shp   # Source Esri Shapefile(s)
- DestDataset_FBX_7 = C:\Users\odawkins\Desktop\SmallAreaPopulationStatistics   # Destination FBX Folder
- DestDataset_CSV2_2 = C:\Users\odawkins\Desktop\PlanningApps   # Destination CSV (Comma Separated Value) Folder
- SourceDataset_ESRISHAPE_10 = C:\Users\odawkins\Dropbox\Building_City_Dashboards\Data\2019_06_19_BCD_3D_Data_Layers_REVISED\National_Monuments_Service\National_Monuments.shp   # Source Esri Shapefile(s)
- SourceDataset_OBJ = C:\Users\odawkins\Dropbox\Building_City_Dashboards\Data\2019_06_19_BCD_3D_Data_Layers_REVISED\3D_Marker\marker_blue.obj   # Source OBJ File
- SourceDataset_CSV2_5 = C:\Users\odawkins\Dropbox\Building_City_Dashboards\Data\2019_06_19_BCD_3D_Data_Layers_REVISED\Small_Areas_Population_Statistics_CSO\SAPS2016_SA2017.csv   # Source CSV (Comma Separated Value) File(s)
- DestDataset_FBX_11 = C:\Users\odawkins\Desktop\National_Monuments   # Destination FBX Folder
- SourceDataset_ESRISHAPE_12 = C:\Users\odawkins\Dropbox\Building_City_Dashboards\Data\2019_06_19_BCD_3D_Data_Layers_REVISED\Price_Paid_Register\Geolocated_PPR_2016Q1_2019Q1\PPR_2016Q1_2019Q1_All.shp   # Source Esri Shapefile(s)
- DestDataset_CSV2_18 = C:\Users\odawkins\Desktop\National_Monuments   # Destination CSV (Comma Separated Value) Folder
- DestDataset_FBX_8 = C:\Users\odawkins\Desktop\PricePaidRegister   # Destination FBX Folder
- DestDataset_CSV2_16 = C:\Users\odawkins\Desktop\PricePaidRegister   # Destination CSV (Comma Separated Value) Folder
- DestDataset_FBX_10 = C:\Users\odawkins\Desktop\Architectural_Heritage   # Destination FBX Folder
- DestDataset_CSV2_14 = C:\Users\odawkins\Desktop\Architectural_Heritage   # Destination CSV (Comma Separated Value) Folder
- DestDataset_CSV2_20 = C:\Users\odawkins\Desktop\SmallAreaPopulationStatistics   # Destination CSV (Comma Separated Value) Folder
- DestDataset_CSV2_15 = C:\Users\odawkins\Desktop\SmallAreaPopulationStatistics   # Destination CSV (Comma Separated Value) Folder
- DestDataset_JSON = C:\Users\odawkins\Desktop\SmallAreaPopulationStatistics\SAPS_2016.json   # Destination JSON (JavaScript Object Notation) File
- SourceDataset_CSV2_4 = C:\Users\odawkins\Dropbox\Building_City_Dashboards\Data\2019_06_19_BCD_3D_Data_Layers_REVISED\Small_Areas_Population_Statistics_CSO\Census_2011\AllThemesTablesSA.csv   # Source CSV (Comma Separated Value) File(s)
- DestDataset_CSV2_3 = C:\Users\odawkins\Desktop\SmallAreaPopulationStatistics   # Destination CSV (Comma Separated Value) Folder
- DestDataset_ESRISHAPE = C:\Users\odawkins\Desktop\SmallAreaPopulationStatistics\SAPS_2016_ShapeFile   # Destination Esri Shapefile Folder
- DestDataset_CSV2_17 = C:\Users\odawkins\Desktop\SmallAreaPopulationStatistics   # Destination CSV (Comma Separated Value) Folder
- DestDataset_CSV2_19 = C:\Users\odawkins\Desktop\SmallAreaPopulationStatistics   # Destination CSV (Comma Separated Value) Folder
- SourceDataset_ESRISHAPE_14 = C:\Users\odawkins\Dropbox\Building_City_Dashboards\Data\2019_08_28_Dublin_Extent_7x4km_1_2000_padding_1km\Dublin Extent 7x4km 1_2000 padding 1km\Dublin Extent 7x4km 1_2000 padding 1km.shp   # Source Esri Shapefile(s)
- SourceDataset_ESRISHAPE_9 = C:\Users\odawkins\Dropbox\Building_City_Dashboards\Data\2019_06_19_BCD_3D_Data_Layers_REVISED\National_Inventory_of_Architectural_Heritage\NIAH_Sites.shp   # Source Esri Shapefile(s)

Readers:
- ESRISHAPE_1: ESRISHAPE from $(SourceDataset_ESRISHAPE)
- CSV2_1: CSV2 from $(SourceDataset_CSV2)
- ESRISHAPE_2: ESRISHAPE from $(SourceDataset_ESRISHAPE_15)
- ESRISHAPE_3: ESRISHAPE from $(SourceDataset_ESRISHAPE_13)
- ESRISHAPE_4: ESRISHAPE from $(SourceDataset_ESRISHAPE_11)
- CSV2_2: CSV2 from $(SourceDataset_CSV2_5)
- ESRISHAPE_5: ESRISHAPE from $(SourceDataset_ESRISHAPE_9)
- ESRISHAPE_6: ESRISHAPE from $(SourceDataset_ESRISHAPE_10)
- OBJ_1: OBJ from $(SourceDataset_OBJ)
- ESRISHAPE_7: ESRISHAPE from $(SourceDataset_ESRISHAPE_12)
- CSV2_3: CSV2 from $(SourceDataset_CSV2_4)
- ESRISHAPE_8: ESRISHAPE from $(SourceDataset_ESRISHAPE_14)

Writers:
- FBX_1: FBX to $(DestDataset_FBX) in EPSG:2157
- CSV2_4: CSV2 to $(DestDataset_CSV2)
- FBX_2: FBX to $(DestDataset_FBX_9) in EPSG:2157
- CSV2_5: CSV2 to $(DestDataset_CSV2_2)
- FBX_3: FBX to $(DestDataset_FBX_7) in EPSG:2157
- FBX_4: FBX to $(DestDataset_FBX_11) in EPSG:2157
- CSV2_6: CSV2 to $(DestDataset_CSV2_18)
- FBX_5: FBX to $(DestDataset_FBX_8) in EPSG:2157
- CSV2_7: CSV2 to $(DestDataset_CSV2_16)
- FBX_6: FBX to $(DestDataset_FBX_10) in EPSG:2157
- CSV2_8: CSV2 to $(DestDataset_CSV2_14)
- CSV2_9: CSV2 to $(DestDataset_CSV2_3)
- CSV2_10: CSV2 to $(DestDataset_CSV2_20)
- CSV2_11: CSV2 to $(DestDataset_CSV2_15)
- JSON_1: JSON to $(DestDataset_JSON)
- ESRISHAPE_9: ESRISHAPE to $(DestDataset_ESRISHAPE)
- CSV2_12: CSV2 to $(DestDataset_CSV2_17)
- CSV2_13: CSV2 to $(DestDataset_CSV2_19)

Note: Small Area Measures / 1. Population density (per km sq) - DONE / 2. Dependency ratio (per 100) - DONE / 3. Percentage non Irish National - DONE / 4. Households built to 2000 - DONE / 5. Households built from 2001 - DONE / 6. Percentage Households Flats/Apartments/Bedsits - DONE / 7. Percentage of Rented Households - DONE / 8. Percentage of Vacant Households (excluding holiday homes) - DONE / 9. Percentage of Unemployed - DONE / 10. Percentage of social class A, B (Professional, Management and Technical) - DONE / 11. Percentage of social class C to Z (Other) - DONE / 12. Percentage with third level education - DONE / 13. Percentage without third level education - DONE / 14. Average number of persons per household - DONE / 15. Percentage of households without internet - DONE / 16. Percentage of persons with a disability - DONE / 17. Percentage change population 2011-2016 - DONE / 18. Percentage change in the number of households 2011-1016 / 19. Number of people working in SA from outside 4 LAs - AWAITING DATA FROM AIRO (POWCAR) / Note: All measures counted by household where applicable
Junction
    -> Clipper_2 [CLIPPER]
    -> Clipper [CLIPPER]
    -> Clipper_3 [CLIPPER]
    -> Clipper_4 [CLIPPER]
    -> Clipper_5 [CLIPPER]
    -> Clipper_7 [CLIPPER]

Bookmark: Projection Mapping Boundary
Dublin Extent 7x4km 1_2000 padding 1km (reader ESRISHAPE_8)
    attributes: left double, top double, right double, bottom double, id long
    -> Junction

Bookmark: Dublin Centre 3D Model Boundary
BCD_Boundary (reader ESRISHAPE_2) [off]
    attributes: Small_Area long, Small_Ar_1 char(80), Small_Ar_2 char(80), Small_Ar_3 char(80), Small_Ar_4 char(80), Small_Ar_5 char(80), Small_Ar_6 char(80), Small_Ar_7 char(80), Small_Ar_8 char(80), Small_Ar_9 char(80), Small_A_10 char(80), Small_A_11 char(80), Small_A_12 char(80), Small_A_13 char(80), Small_A_14 char(80), Small_A_15 char(80), Small_A_16 long, Small_A_17 long, Small_A_18 long, Small_A_19 double, Small_A_20 double, SAPS_2016_ char(254), SAPS_20161 char(254), SAPS_20162 char(254), SAPS_20163 long
    -> Junction

Bookmark: Development Plan Shapefile
Note: Data Source: / https://data.smartdublin.ie/dataset/development-plans-dublin-city / File: DCCDevelopmentPlan_P20141002-1159.shp
dccdevelopmentplanp20141002-1159 (reader ESRISHAPE_1)
    attributes: OBJECTID long, ZONE_ORIG char(254), ZONE_GZT char(4), ZONE_DESC char(254), ZONE_LINK char(254), COLOUR char(100)
    -> Reprojector
Note: Data Source: / https://data.smartdublin.ie/dataset/development-plans-dublin-city / File: DublinCityPlanZones_GZT_P20141016-1441.xlsx / NOTE: Data has been cleaned to remove formatting, empty values and leading whitespace. Saved as CSV.
CSV (reader CSV2_1)
    attributes: GZTNo string, GZT_CATEGORY   string
    -> FeatureJoiner [RIGHT]

Bookmark: Reproject Data
Note: Reprojector Parameters: / 1. Destination Coordinate System = EPSG:2157
Reprojector
    DEST = EPSG:2157
    INTERPOLATION_TYPE_NAME = Nearest Neighbor
    RASTER_CELL_SIZE = Preserve Cells
    RASTER_TOLERANCE = 0.0
    SOURCE = Read from feature
    REPROJECTED -> Clipper [CLIPPEE]

Bookmark: Clip spatial data to boundary
Note: Clipper Parameters: / 1. Clippees on Clipper Boundary = Treat as Inside
Clipper
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> Deaggregator_3

Bookmark: Remove Duplicate Shapes Created by Clipper
Note: Deaggregator Parameters: / 1. DEFAULT
Deaggregator_3
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AreaCalculator_3
Note: Area Calculator Parameters: / 1. Area attribute = _area
AreaCalculator_3
    AREA_ATTR = _area
    AREA_TYPE = Plane Area
    MULT = 1
    -> Sorter_3
Note: Sorter Parameters: / 1. Sort by = _area / Numeric / Descending
Note: NOTE: This is a workaround to remove multiple geometries that with the same ID that are created by the processing of clipping when it separates two parts of the same geographic feature by removing their joing geometry. This process simply removes the smaller of the the parts. A preferred solution would be to merge the resulting geomtries and flattern the hierarchy prior to export as FBX.
Sorter_3
    SORT_PARM = _area NUMERIC DESCENDING
    SORTED -> DuplicateFilter_3
Note: Duplicate Filter Parameters: / 1. Key Attributes = OBJECTID
DuplicateFilter_3
    INPUT_ORDERED_CHOICE = No
    KEYATTR = OBJECTID
    UNIQUE -> 3DForcer

Bookmark: Convert 2D polygons to 3D objects
Note: 3D Forcer Parameters: / 1. Elevation = 0
3DForcer
    KEEPZVAL = No
    ZVALATTR = 0
    -> Extruder
Note: Extruder Parameters: / 1. Direction = Vertical / 2. Distance = 1 (metres)
Extruder
    DIRECTION = Vertical
    DISTANCE = 1
    EXTRUDED -> GeometryPropertySetter

Bookmark: Data Processing
Note: Geometry Property Setter Parameters: / 1. Property to Set = Geometry Name / 2. Geometry Name = OBJECTID
GeometryPropertySetter
    GEOM_NAME_FIELD = @Value(OBJECTID)
    OVERWRITE_CHOICE = Yes
    SETTYPE_PARAM = Geometry Name
    SET -> Inspector
    SET -> FeatureJoiner [LEFT]
    SET -> DevPlan (writer FBX_1)
Note: Feature Joiner Parameters: / 1. Join on Zone_GZT and GTZNo
FeatureJoiner
    ATTR_CONFLICT_RES = Use Left
    GEOMETRY_HANDLING = Use Left
    JOIN_KEYS = ZONE_GZT GZTNo AUTO
    JOIN_MODE = Inner
    JOINED -> DEVPlan (writer CSV2_4)

Bookmark: File Outputs
Inspector
Note: FBX Writer Parameters: / 1. SET OUTPUT FILE LOCATION / 2. Coordinate System = EPSG:2157 / 3. Move to Local Coordinate System = No
DevPlan (writer FBX_1)
Note: CSV Writer Parameters: / 1. SET OUTPUT FILE LOCATION / 2. Removed 'ZONE_LINK', '_clipped' and 'GZT_CATEGORY' fields from output. / 3. Reordered output.
DEVPlan (writer CSV2_4)
    attributes: OBJECTID string, ZONE_ORIG string, ZONE_GZT string, GZT_CATEGORY   string, ZONE_DESC string, COLOUR string

Bookmark: Planning Applications Shapefile
Note: Data Source: / https://data.smartdublin.ie/dataset/dublin-city-council-planning-applications / File: DCC_PlanApps.shp
DCC_PlanAppsREPROJECTED (reader ESRISHAPE_3)
    attributes: PLAN_REF char(20), FGDATE char(20), PROPOSAL char(22), LONG_PROPO char(20), APPDATE char(20), LOCATION char(22), STAGE char(20), DECDATE char(20), REGDATE char(20), APPTYPE char(20), DECISION char(20)
    -> Clipper_2 [CLIPPEE]

Bookmark: Clip spatial data to boundary
Note: Clipper Parameters: / 1. Clippees on Clipper Boundary = Treat as Inside
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> Deaggregator_2

Bookmark: Remove Duplicate Shapes Created by Clipper
Note: Deaggregator Parameters: / 1. DEFAULT
Deaggregator_2
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AreaCalculator_2
Note: Area Calculator Parameters: / 1. Area attribute = _area
AreaCalculator_2
    AREA_ATTR = _area
    AREA_TYPE = Plane Area
    MULT = 1
    -> Sorter_2
Note: Sorter Parameters: / 1. Sort by = _area / Numeric / Descending
Note: NOTE: This is a workaround to remove multiple geometries that with the same ID that are created by the processing of clipping when it separates two parts of the same geographic feature by removing their joing geometry. This process simply removes the smaller of the the parts. A preferred solution would be to merge the resulting geomtries and flattern the hierarchy prior to export as FBX.
Sorter_2
    SORT_PARM = _area NUMERIC DESCENDING
    SORTED -> DuplicateFilter_2
Note: Duplicate Filter Parameters: / 1.KeyAttributes = PLAN_REF
DuplicateFilter_2
    INPUT_ORDERED_CHOICE = No
    KEYATTR = PLAN_REF
    UNIQUE -> 3DForcer_2

Bookmark: Convert 2D polygons to 3D objects
Note: 3D Forcer Parameters: / 1. Elevation = 0
3DForcer_2
    KEEPZVAL = No
    ZVALATTR = 0
    -> Extruder_2
Note: Extruder Parameters: / 1. Direction = Vertical / 2. Distance = 1 (metres)
Extruder_2
    DIRECTION = Vertical
    DISTANCE = 1
    EXTRUDED -> GeometryPropertySetter_2

Bookmark: Data Processing
Note: Geometry Property Setter Parameters: / 1. Property to Set = Geometry Name / 2. Geometry Name = PLAN_REF
GeometryPropertySetter_2
    GEOM_NAME_FIELD = @Value(PLAN_REF)
    OVERWRITE_CHOICE = Yes
    SETTYPE_PARAM = Geometry Name
    SET -> DCC_PlanApps (writer FBX_2)
    SET -> Inspector_2
    SET -> DCC_PlanApps (writer CSV2_5)

Bookmark: File Outputs
Inspector_2
Note: FBX Writer Parameters: / 1. SET OUTPUT FILE LOCATION / 2. Coordinate System = EPSG:2157 / 3. Move to Local Coordinate System = No
DCC_PlanApps (writer FBX_2)
Note: CSV Writer Parameters: / 1. SET OUTPUT FILE LOCATION / 2. Removed empty 'LONG_PROPO' field from output.
DCC_PlanApps (writer CSV2_5)
    attributes: PLAN_REF string, FGDATE string, PROPOSAL string, APPDATE string, LOCATION string, STAGE string, DECDATE string, REGDATE string, APPTYPE string, DECISION string

Bookmark: Small Area Population Statistics
Note: Data Source: / https://data.gov.ie/dataset/small-areas-generalised-20m-osi-national-statistical-boundaries-2015 / File: / Small_Areas__Generalised_20m__OSi_National_Boundaries.shp
Small_Areas__Generalised_20m__OSi_National_Boundaries (reader ESRISHAPE_4)
    attributes: OBJECTID long, GUID char(80), NUTS1 char(80), NUTS1NAME char(80), NUTS2 char(80), NUTS2NAME char(80), NUTS3 char(80), NUTS3NAME char(80), COUNTY char(80), COUNTYNAME char(80), CSOED char(80), OSIED char(80), EDNAME char(80), SA_PUB2011 char(80), SMALL_AREA char(80), GEOGID char(80), AREA long, CHANGECODE long, ESRI_OID long, Shape__Are double, Shape__Len double
    -> Reprojector_2
Note: Data Source: / https://cso.ie/en/census/census2016reports/census2016smallareapopulationstatistics/ / File: / SAPS2016_SA2017.csv / Glossary: / SAPS_2016_Glossary.xlsx / NOTE: The Glossary contains the definitions for Census codes used as column names in the main census csv.
CSV (reader CSV2_2)
    attributes: GUID string, GEOGID string, GEOGDESC string, T1_1AGE0M string, T1_1AGE1M string, T1_1AGE2M string, T1_1AGE3M string, T1_1AGE4M string, T1_1AGE5M string, T1_1AGE6M string, T1_1AGE7M string, T1_1AGE8M string, T1_1AGE9M string, T1_1AGE10M string, T1_1AGE11M string, T1_1AGE12M string, T1_1AGE13M string, T1_1AGE14M string, T1_1AGE15M string, T1_1AGE16M string, T1_1AGE17M string, T1_1AGE18M string, T1_1AGE19M string, T1_1AGE20_24M string, T1_1AGE25_29M string, T1_1AGE30_34M string, T1_1AGE35_39M string, T1_1AGE40_44M string, T1_1AGE45_49M string, T1_1AGE50_54M string,
      T1_1AGE55_59M string, T1_1AGE60_64M string, T1_1AGE65_69M string, T1_1AGE70_74M string, T1_1AGE75_79M string, T1_1AGE80_84M string, T1_1AGEGE_85M string, T1_1AGETM string, T1_1AGE0F string, T1_1AGE1F string, T1_1AGE2F string, T1_1AGE3F string, T1_1AGE4F string, T1_1AGE5F string, T1_1AGE6F string, T1_1AGE7F string, T1_1AGE8F string, T1_1AGE9F string, T1_1AGE10F string, T1_1AGE11F string, T1_1AGE12F string, T1_1AGE13F string, T1_1AGE14F string, T1_1AGE15F string, T1_1AGE16F string, T1_1AGE17F string, T1_1AGE18F string, T1_1AGE19F string, T1_1AGE20_24F string, T1_1AGE25_29F string,
      T1_1AGE30_34F string, T1_1AGE35_39F string, T1_1AGE40_44F string, T1_1AGE45_49F string, T1_1AGE50_54F string, T1_1AGE55_59F string, T1_1AGE60_64F string, T1_1AGE65_69F string, T1_1AGE70_74F string, T1_1AGE75_79F string, T1_1AGE80_84F string, T1_1AGEGE_85F string, T1_1AGETF string, T1_1AGE0T string, T1_1AGE1T string, T1_1AGE2T string, T1_1AGE3T string, T1_1AGE4T string, T1_1AGE5T string, T1_1AGE6T string, T1_1AGE7T string, T1_1AGE8T string, T1_1AGE9T string, T1_1AGE10T string, T1_1AGE11T string, T1_1AGE12T string, T1_1AGE13T string, T1_1AGE14T string, T1_1AGE15T string, T1_1AGE16T string,
      T1_1AGE17T string, T1_1AGE18T string, T1_1AGE19T string, T1_1AGE20_24T string, T1_1AGE25_29T string, T1_1AGE30_34T string, T1_1AGE35_39T string, T1_1AGE40_44T string, T1_1AGE45_49T string, T1_1AGE50_54T string, T1_1AGE55_59T string, T1_1AGE60_64T string, T1_1AGE65_69T string, T1_1AGE70_74T string, T1_1AGE75_79T string, T1_1AGE80_84T string, T1_1AGEGE_85T string, T1_1AGETT string, T1_2SGLM string, T1_2MARM string, T1_2SEPM string, T1_2DIVM string, T1_2WIDM string, T1_2TM string, T1_2SGLF string, T1_2MARF string, T1_2SEPF string, T1_2DIVF string, T1_2WIDF string, T1_2TF string,
      T1_2SGLT string, T1_2MART string, T1_2SEPT string, T1_2DIVT string, T1_2WIDT string, T1_2T string, T2_1IEBP string, T2_1UKBP string, T2_1PLBP string, T2_1LTBP string, T2_1EUBP string, T2_1RWBP string, T2_1TBP string, T2_1IEN string, T2_1UKN string, T2_1PLN string, T2_1LTN string, T2_1EUN string, T2_1RWN string, T2_1NSN string, T2_1TN string, T2_2WI string, T2_2WIT string, T2_2OW string, T2_2BBI string, T2_2AAI string, T2_2OTH string, T2_2NS string, T2_2T string, T2_3SA string,
      T2_3EC string, T2_3EI string, T2_3OI string, T2_3T string, T2_4CA string, T2_4OR string, T2_4NR string, T2_4NS string, T2_4T string, T2_5PL string, T2_5FR string, T2_5LT string, T2_5OTH string, T2_5T string, T2_6VW string, T2_6W string, T2_6NW string, T2_6NAA string, T2_6NS string, T2_6T string, T3_1YES string, T3_1NO string, T3_1NS string, T3_1T string, T3_2DIM string, T3_2DIDOM string, T3_2DIWOM string, T3_2DILOOM string, T3_2DINOM string, T3_2DOESM string,
      T3_2WOESM string, T3_2LOOESM string, T3_2NOESM string, T3_2NSM string, T3_2ALLM string, T3_2DIF string, T3_2DIDOF string, T3_2DIWOF string, T3_2DILOOF string, T3_2DINOF string, T3_2DOESF string, T3_2WOESF string, T3_2LOOESF string, T3_2NOESF string, T3_2NSF string, T3_2ALLF string, T3_2DIT string, T3_2DIDOT string, T3_2DIWOT string, T3_2DILOOT string, T3_2DINOT string, T3_2DOEST string, T3_2WOEST string, T3_2LOOEST string, T3_2NOEST string, T3_2NST string, T3_2ALLT string, T4_1_2PF string, T4_1_3PF string, T4_1_4PF string,
      T4_1_5PF string, T4_1_GRE_6PF string, T4_1_TF string, T4_1_2PP string, T4_1_3PP string, T4_1_4PP string, T4_1_5PP string, T4_1_GRE_6PP string, T4_1_TP string, T4_1_2PC string, T4_1_3PC string, T4_1_4PC string, T4_1_5PC string, T4_1_GRE_6PC string, T4_1_TC string, T4_2_1CU15 string, T4_2_2CU15 string, T4_2_3CU15 string, T4_2_4CU15 string, T4_2_GE5CU15 string, T4_2_TCU15 string, T4_2_1CO15 string, T4_2_2CO15 string, T4_2_3CO15 string, T4_2_4CO15 string, T4_2_GE5CO15 string, T4_2_TCO15 string, T4_2_2CUO15 string, T4_2_3CUO15 string, T4_2_4CUO15 string,
      T4_2_GE5CUO15 string, T4_2_TCUO15 string, T4_2_NCT string, T4_2_1CT string, T4_2_2CT string, T4_2_3CT string, T4_2_4CT string, T4_2_GE5CT string, T4_2_TCT string, T4_3FCCU15 string, T4_3FCCO15 string, T4_3FCCUO15 string, T4_3FCCT string, T4_3FOPMCU15 string, T4_3FOPMCO15 string, T4_3FOPMCUO15 string, T4_3FOPMCT string, T4_3FOPFCU15 string, T4_3FOPFCO15 string, T4_3FOPFCUO15 string, T4_3FOPFCT string, T4_3CCCU15 string, T4_3CCCO15 string, T4_3CCCUO15 string, T4_3CCCT string, T4_3COPMCU15 string, T4_3COPMCO15 string, T4_3COPMCUO15 string, T4_3COPMCT string, T4_3COPFCU15 string,
      T4_3COPFCO15 string, T4_3COPFCUO15 string, T4_3COPFCT string, T4_4AGE0_4F string, T4_4AGE5_9F string, T4_4AGE10_14F string, T4_4AGE15_19F string, T4_4AGE_GE20F string, T4_4TF string, T4_4AGE0_4P string, T4_4AGE5_9P string, T4_4AGE10_14P string, T4_4AGE15_19P string, T4_4AGE_GE20P string, T4_4TP string, T4_5PFF string, T4_5ENF string, T4_5RF string, T4_5PSF string, T4_5ESF string, T4_5PAF string, T4_5ADOF string, T4_5ADUF string, T4_5TF string, T4_5PFP string, T4_5ENP string, T4_5RP string, T4_5PSP string, T4_5ESP string, T4_5PAP string,
      T4_5ADOP string, T4_5ADUP string, T4_5TP string, T4_6_0C string, T4_6_1C string, T4_6_2C string, T4_6_3C string, T4_6_GE4C string, T4_6T string, T5_1OP_H string, T5_1MC_H string, T5_1CC_H string, T5_1MCC_H string, T5_1CCC_H string, T5_1OPFC_H string, T5_1OPMC_H string, T5_1CO_H string, T5_1CCO_H string, T5_1OPFCO_H string, T5_1OPMCO_H string, T5_1GETFU_H string, T5_1NHR_H string, T5_1GENP_H string, T5_1T_H string, T5_1OP_P string, T5_1MC_P string, T5_1CC_P string, T5_1MCC_P string, T5_1CCC_P string, T5_1OPFC_P string,
      T5_1OPMC_P string, T5_1CO_P string, T5_1CCO_P string, T5_1OPFCO_P string, T5_1OPMCO_P string, T5_1GETFU_P string, T5_1NHR_P string, T5_1GENP_P string, T5_1T_P string, T5_2_1PH string, T5_2_2PH string, T5_2_3PH string, T5_2_4PH string, T5_2_5PH string, T5_2_6PH string, T5_2_7PH string, T5_2_GE8PH string, T5_2_TH string, T5_2_1PP string, T5_2_2PP string, T5_2_3PP string, T5_2_4PP string, T5_2_5PP string, T5_2_6PP string, T5_2_7PP string, T5_2_GE8PP string, T5_2_TP string, T6_1_HB_H string, T6_1_FA_H string, T6_1_BS_H string,
      T6_1_CM_H string, T6_1_NS_H string, T6_1_TH string, T6_1_HB_P string, T6_1_FA_P string, T6_1_BS_P string, T6_1_CM_P string, T6_1_NS_P string, T6_1_TP string, T6_2_PRE19H string, T6_2_19_45H string, T6_2_46_60H string, T6_2_61_70H string, T6_2_71_80H string, T6_2_81_90H string, T6_2_91_00H string, T6_2_01_10H string, T6_2_11LH string, T6_2_NSH string, T6_2_TH string, T6_2_PRE19P string, T6_2_19_45P string, T6_2_46_60P string, T6_2_61_70P string, T6_2_71_80P string, T6_2_81_90P string, T6_2_91_00P string, T6_2_01_10P string, T6_2_11LP string, T6_2_NSP string,
      T6_2_TP string, T6_3_OMLH string, T6_3_OOH string, T6_3_RPLH string, T6_3_RLAH string, T6_3_RVCHBH string, T6_3_OFRH string, T6_3_NSH string, T6_3_TH string, T6_3_OMLP string, T6_3_OOP string, T6_3_RPLP string, T6_3_RLAP string, T6_3_RVCHBP string, T6_3_OFRP string, T6_3_NSP string, T6_3_TP string, T6_4_1RH string, T6_4_2RH string, T6_4_3RH string, T6_4_4RH string, T6_4_5RH string, T6_4_6RH string, T6_4_7RH string, T6_4_GE8RH string, T6_4_NSH string, T6_4_TH string, T6_4_1RP string, T6_4_2RP string, T6_4_3RP string,
      T6_4_4RP string, T6_4_5RP string, T6_4_6RP string, T6_4_7RP string, T6_4_GE8RP string, T6_4_NSP string, T6_4_TP string, T6_5_NCH string, T6_5_OCH string, T6_5_NGCH string, T6_5_ECH string, T6_5_CCH string, T6_5_PCH string, T6_5_LPGCH string, T6_5_WCH string, T6_5_OTH string, T6_5_NS string, T6_5_T string, T6_6_PM string, T6_6_GSLA string, T6_6_GSP string, T6_6_OP string, T6_6_N string, T6_6_NS string, T6_6_T string, T6_7_PS string, T6_7_IST string, T6_7_OIT string, T6_7_OTH string, T6_7_NSF string,
      T6_7_NS string, T6_7_T string, T6_8_O string, T6_8_TA string, T6_8_UHH string, T6_8_OVD string, T6_8_T string, T7_1_NE string, T7_1_NP string, T8_1_WM string, T8_1_LFFJM string, T8_1_ULGUPJM string, T8_1_SM string, T8_1_LAHFM string, T8_1_RM string, T8_1_UTWSDM string, T8_1_OTHM string, T8_1_TM string, T8_1_WF string, T8_1_LFFJF string, T8_1_ULGUPJF string, T8_1_SF string, T8_1_LAHFF string, T8_1_RF string, T8_1_UTWSDF string, T8_1_OTHF string, T8_1_TF string, T8_1_WT string, T8_1_LFFJT string, T8_1_ULGUPJT string,
      T8_1_ST string, T8_1_LAHFT string, T8_1_RT string, T8_1_UTWSDT string, T8_1_OTHT string, T8_1_TT string, T9_1_PWM string, T9_1_MTM string, T9_1_NMM string, T9_1_SM string, T9_1_SSM string, T9_1_USM string, T9_1_OTHGEUM string, T9_1_TM string, T9_1_PWF string, T9_1_MTF string, T9_1_NMF string, T9_1_SF string, T9_1_SSF string, T9_1_USF string, T9_1_OTHGEUF string, T9_1_TF string, T9_1_PWT string, T9_1_MTT string, T9_1_NMT string, T9_1_ST string, T9_1_SST string, T9_1_UST string, T9_1_OTHGEUT string, T9_1_TT string,
      T9_2_HA string, T9_2_HB string, T9_2_HC string, T9_2_HD string, T9_2_HE string, T9_2_HF string, T9_2_HG string, T9_2_HH string, T9_2_HI string, T9_2_HJ string, T9_2_HZ string, T9_2_HT string, T9_2_PA string, T9_2_PB string, T9_2_PC string, T9_2_PD string, T9_2_PE string, T9_2_PF string, T9_2_PG string, T9_2_PH string, T9_2_PI string, T9_2_PJ string, T9_2_PZ string, T9_2_PT string, T10_1_LT15M string, T10_1_15M string, T10_1_16M string, T10_1_17M string, T10_1_18M string, T10_1_19M string,
      T10_1_20M string, T10_1_GE21M string, T10_1_NSM string, T10_1_TM string, T10_1_LT15F string, T10_1_15F string, T10_1_16F string, T10_1_17F string, T10_1_18F string, T10_1_19F string, T10_1_20F string, T10_1_GE21F string, T10_1_NSF string, T10_1_TF string, T10_1_LT15T string, T10_1_15T string, T10_1_16T string, T10_1_17T string, T10_1_18T string, T10_1_19T string, T10_1_20T string, T10_1_GE21T string, T10_1_NST string, T10_1_TT string, T10_2_SASM string, T10_2_OTHM string, T10_2_SASF string, T10_2_OTHF string, T10_2_SAST string, T10_2_OTHT string,
      T10_3_EDUM string, T10_3_ARTM string, T10_3_HUMM string, T10_3_SOCM string, T10_3_SCIM string, T10_3_ENGM string, T10_3_AGRM string, T10_3_HEAM string, T10_3_SERM string, T10_3_OTHM string, T10_3_NSM string, T10_3_TM string, T10_3_EDUF string, T10_3_ARTF string, T10_3_HUMF string, T10_3_SOCF string, T10_3_SCIF string, T10_3_ENGF string, T10_3_AGRF string, T10_3_HEAF string, T10_3_SERF string, T10_3_OTHF string, T10_3_NSF string, T10_3_TF string, T10_3_EDUT string, T10_3_ARTT string, T10_3_HUMT string, T10_3_SOCT string, T10_3_SCIT string, T10_3_ENGT string,
      T10_3_AGRT string, T10_3_HEAT string, T10_3_SERT string, T10_3_OTHT string, T10_3_NST string, T10_3_TT string, T10_4_NFM string, T10_4_PM string, T10_4_LSM string, T10_4_USM string, T10_4_TVM string, T10_4_ACCAM string, T10_4_HCM string, T10_4_ODNDM string, T10_4_HDPQM string, T10_4_PDM string, T10_4_DM string, T10_4_NSM string, T10_4_TM string, T10_4_NFF string, T10_4_PF string, T10_4_LSF string, T10_4_USF string, T10_4_TVF string, T10_4_ACCAF string, T10_4_HCF string, T10_4_ODNDF string, T10_4_HDPQF string, T10_4_PDF string, T10_4_DF string,
      T10_4_NSF string, T10_4_TF string, T10_4_NFT string, T10_4_PT string, T10_4_LST string, T10_4_UST string, T10_4_TVT string, T10_4_ACCAT string, T10_4_HCT string, T10_4_ODNDT string, T10_4_HDPQT string, T10_4_PDT string, T10_4_DT string, T10_4_NST string, T10_4_TT string, T11_1_FW string, T11_1_BIW string, T11_1_BUW string, T11_1_TDLW string, T11_1_MW string, T11_1_CDW string, T11_1_CPW string, T11_1_VW string, T11_1_OTHW string, T11_1_WMFHW string, T11_1_NSW string, T11_1_TW string, T11_1_FS string, T11_1_BIS string, T11_1_BUS string,
      T11_1_TDLS string, T11_1_MS string, T11_1_CDS string, T11_1_CPS string, T11_1_VS string, T11_1_OTHS string, T11_1_WMFHS string, T11_1_NSS string, T11_1_TS string, T11_1_FT string, T11_1_BIT string, T11_1_BUT string, T11_1_TDLT string, T11_1_MT string, T11_1_CDT string, T11_1_CPT string, T11_1_VT string, T11_1_OTHT string, T11_1_WMFHT string, T11_1_NST string, T11_1_TT string, T11_2_T1 string, T11_2_T2 string, T11_2_T3 string, T11_2_T4 string, T11_2_T5 string, T11_2_T6 string, T11_2_T7 string, T11_2_T8 string, T11_2_NS string,
      T11_2_T string, T11_3_D1 string, T11_3_D2 string, T11_3_D3 string, T11_3_D4 string, T11_3_D5 string, T11_3_D6 string, T11_3_NS string, T11_3_T string, T12_1_M string, T12_1_F string, T12_1_T string, T12_2_M string, T12_2_F string, T12_2_T string, T12_3_VGM string, T12_3_VGF string, T12_3_VGT string, T12_3_GM string, T12_3_GF string, T12_3_GT string, T12_3_FM string, T12_3_FF string, T12_3_FT string, T12_3_BM string, T12_3_BF string, T12_3_BT string, T12_3_VBM string, T12_3_VBF string, T12_3_VBT string,
      T12_3_NSM string, T12_3_NSF string, T12_3_NST string, T12_3_TM string, T12_3_TF string, T12_3_TT string, T13_1_MDSOM string, T13_1_POM string, T13_1_APTOM string, T13_1_ASOM string, T13_1_STOM string, T13_1_CLOSOM string, T13_1_SCSOM string, T13_1_PPMOM string, T13_1_EOM string, T13_1_NSM string, T13_1_TM string, T13_1_MDSOF string, T13_1_POF string, T13_1_APTOF string, T13_1_ASOF string, T13_1_STOF string, T13_1_CLOSOF string, T13_1_SCSOF string, T13_1_PPMOF string, T13_1_EOF string, T13_1_NSF string, T13_1_TF string, T13_1_MDSOT string, T13_1_POT string,
      T13_1_APTOT string, T13_1_ASOT string, T13_1_STOT string, T13_1_CLOSOT string, T13_1_SCSOT string, T13_1_PPMOT string, T13_1_EOT string, T13_1_NST string, T13_1_TT string, T14_1_AFFM string, T14_1_BCM string, T14_1_MIM string, T14_1_CTM string, T14_1_TCM string, T14_1_PAM string, T14_1_PSM string, T14_1_OTHM string, T14_1_TM string, T14_1_AFFF string, T14_1_BCF string, T14_1_MIF string, T14_1_CTF string, T14_1_TCF string, T14_1_PAF string, T14_1_PSF string, T14_1_OTHF string, T14_1_TF string, T14_1_AFFT string, T14_1_BCT string, T14_1_MIT string,
      T14_1_CTT string, T14_1_TCT string, T14_1_PAT string, T14_1_PST string, T14_1_OTHT string, T14_1_TT string, T15_1_NC string, T15_1_1C string, T15_1_2C string, T15_1_3C string, T15_1_GE4C string, T15_1_NSC string, T15_1_TC string, T15_2_Y string, T15_2_N string, T15_2_NS string, T15_2_T string, T15_3_B string, T15_3_OTH string, T15_3_N string, T15_3_NS string, T15_3_T string
    -> FeatureJoiner_2 [RIGHT]
Note: Data Source: / https://www.cso.ie/en/census/census2011smallareapopulationstatisticssaps/ / File: / AllThemesTablesSA.csv / Glossary: / Theme,breakdown.xlsx / NOTE: The Glossary contains the definitions for Census codes used as column names in the main census csv. Boundary files for 2011 Small areas are also available: / https://www.cso.ie/en/census/census2011boundaryfiles/
CSV (reader CSV2_3)
    attributes: GEOGID string, GEOGTYPE string, GEOGDESC string, T1_1AGE0M string, T1_1AGE1M string, T1_1AGE2M string, T1_1AGE3M string, T1_1AGE4M string, T1_1AGE5M string, T1_1AGE6M string, T1_1AGE7M string, T1_1AGE8M string, T1_1AGE9M string, T1_1AGE10M string, T1_1AGE11M string, T1_1AGE12M string, T1_1AGE13M string, T1_1AGE14M string, T1_1AGE15M string, T1_1AGE16M string, T1_1AGE17M string, T1_1AGE18M string, T1_1AGE19M string, T1_1AGE20_24M string, T1_1AGE25_29M string, T1_1AGE30_34M string, T1_1AGE35_39M string, T1_1AGE40_44M string, T1_1AGE45_49M string, T1_1AGE50_54M string,
      T1_1AGE55_59M string, T1_1AGE60_64M string, T1_1AGE65_69M string, T1_1AGE70_74M string, T1_1AGE75_79M string, T1_1AGE80_84M string, T1_1AGEGE_85M string, T1_1AGETM string, T1_1AGE0F string, T1_1AGE1F string, T1_1AGE2F string, T1_1AGE3F string, T1_1AGE4F string, T1_1AGE5F string, T1_1AGE6F string, T1_1AGE7F string, T1_1AGE8F string, T1_1AGE9F string, T1_1AGE10F string, T1_1AGE11F string, T1_1AGE12F string, T1_1AGE13F string, T1_1AGE14F string, T1_1AGE15F string, T1_1AGE16F string, T1_1AGE17F string, T1_1AGE18F string, T1_1AGE19F string, T1_1AGE20_24F string, T1_1AGE25_29F string,
      T1_1AGE30_34F string, T1_1AGE35_39F string, T1_1AGE40_44F string, T1_1AGE45_49F string, T1_1AGE50_54F string, T1_1AGE55_59F string, T1_1AGE60_64F string, T1_1AGE65_69F string, T1_1AGE70_74F string, T1_1AGE75_79F string, T1_1AGE80_84F string, T1_1AGEGE_85F string, T1_1AGETF string, T1_1AGE0T string, T1_1AGE1T string, T1_1AGE2T string, T1_1AGE3T string, T1_1AGE4T string, T1_1AGE5T string, T1_1AGE6T string, T1_1AGE7T string, T1_1AGE8T string, T1_1AGE9T string, T1_1AGE10T string, T1_1AGE11T string, T1_1AGE12T string, T1_1AGE13T string, T1_1AGE14T string, T1_1AGE15T string, T1_1AGE16T string,
      T1_1AGE17T string, T1_1AGE18T string, T1_1AGE19T string, T1_1AGE20_24T string, T1_1AGE25_29T string, T1_1AGE30_34T string, T1_1AGE35_39T string, T1_1AGE40_44T string, T1_1AGE45_49T string, T1_1AGE50_54T string, T1_1AGE55_59T string, T1_1AGE60_64T string, T1_1AGE65_69T string, T1_1AGE70_74T string, T1_1AGE75_79T string, T1_1AGE80_84T string, T1_1AGEGE_85T string, T1_1AGETT string, T1_2SGLM string, T1_2MARM string, T1_2SEPM string, T1_2DIVM string, T1_2WIDM string, T1_2TM string, T1_2SGLF string, T1_2MARF string, T1_2SEPF string, T1_2DIVF string, T1_2WIDF string, T1_2TF string,
      T1_2SGLT string, T1_2MART string, T1_2SEPT string, T1_2DIVT string, T1_2WIDT string, T1_2T string, T2_1IEBP string, T2_1UKBP string, T2_1PLBP string, T2_1LTBP string, T2_1EUBP string, T2_1RWBP string, T2_1NSBP string, T2_1TBP string, T2_1IEN string, T2_1UKN string, T2_1PLN string, T2_1LTN string, T2_1EUN string, T2_1RWN string, T2_1NSN string, T2_1TN string, T2_2WI string, T2_2WIT string, T2_2OW string, T2_2BBI string, T2_2AAI string, T2_2OTH string, T2_2NS string, T2_2T string,
      T2_3SA string, T2_3EC string, T2_3EI string, T2_3OI string, T2_3T string, T2_4CA string, T2_4OR string, T2_4NR string, T2_4NS string, T2_4T string, T2_5T string, T2_5PL string, T2_5FR string, T2_5LT string, T2_5OTH string, T2_6T string, T2_6VW string, T2_6W string, T2_6NW string, T2_6NAA string, T2_6NS string, T3_1YES string, T3_1NO string, T3_1NS string, T3_1T string, T3_2T string, T3_2DW string, T3_2DWO string, T3_2DO string, T3_2WO string,
      T3_2LO string, T3_2NO string, T3_2NSO string, T3_3DM string, T3_3WM string, T3_3LOM string, T3_3NM string, T3_3TM string, T3_3DF string, T3_3WF string, T3_3LOF string, T3_3NF string, T3_3TF string, T3_3DT string, T3_3WT string, T3_3LOT string, T3_3NT string, T3_3TT string, T4_1_2PF string, T4_1_3PF string, T4_1_4PF string, T4_1_5PF string, T4_1_GRE_6PF string, T4_1_TF string, T4_1_2PP string, T4_1_3PP string, T4_1_4PP string, T4_1_5PP string, T4_1_GRE_6PP string, T4_1_TP string,
      T4_1_2PC string, T4_1_3PC string, T4_1_4PC string, T4_1_5PC string, T4_1_GRE_6PC string, T4_1_TC string, T4_2_NCU15 string, T4_2_1CU15 string, T4_2_2CU15 string, T4_2_3CU15 string, T4_2_4CU15 string, T4_2_GE5U15 string, T4_2_NCO15 string, T4_2_1CO15 string, T4_2_2CO15 string, T4_2_3CO15 string, T4_2_4CO15 string, T4_2_GE5O15 string, T4_2_NCUO15 string, T4_2_1CUO15 string, T4_2_2CUO15 string, T4_2_3CUO15 string, T4_2_4CUO15 string, T4_2_GE5UO15 string, T4_2_NCT string, T4_2_1CT string, T4_2_2CT string, T4_2_3CT string, T4_2_4CT string, T4_2_GE5T string,
      T4_3FLT15C string, T4_3FGE15C string, T4_3FOTH15C string, T4_3FTC string, T4_3FLT15LM string, T4_3FGE15LM string, T4_3FOTH15LM string, T4_3FTLM string, T4_3FLT15LF string, T4_3FGE15LF string, T4_3FOTH15LF string, T4_3FTLF string, T4_3CLT15C string, T4_3CGE15C string, T4_3COTH15C string, T4_3CTC string, T4_3CLT15LM string, T4_3CGE15LM string, T4_3COTH15LM string, T4_3CTLM string, T4_3CLT15LF string, T4_3CGE15LF string, T4_3COTH15LF string, T4_3CTLF string, T4_4AGE0_4F string, T4_4AGE5_9F string, T4_4AGE10_14F string, T4_4AGE15_19F string, T4_4AGE_GE20F string, T4_4TF string,
      T4_4AGE0_4P string, T4_4AGE5_9P string, T4_4AGE10_14P string, T4_4AGE15_19P string, T4_4AGE_GE20P string, T4_4TP string, T4_5PFF string, T4_5ENF string, T4_5RF string, T4_5PSF string, T4_5ESF string, T4_5PAF string, T4_5ADOF string, T4_5ADUF string, T4_5TF string, T4_5PFP string, T4_5ENP string, T4_5RP string, T4_5PSP string, T4_5ESP string, T4_5PAP string, T4_5ADOP string, T4_5ADUP string, T4_5TP string, T4_6_0C string, T4_6_1C string, T4_6_2C string, T4_6_3C string, T4_6_GE4C string, T4_6T string,
      T5_1OP_H string, T5_1HW_H string, T5_1CC_H string, T5_1HWC_H string, T5_1CCC_H string, T5_1FC_H string, T5_1MC_H string, T5_1CO_H string, T5_1CCO_H string, T5_1FCO_H string, T5_1MCO_H string, T5_1GETFU_H string, T5_1NHR_H string, T5_1GENP_H string, T5_1T_H string, T5_1OP_P string, T5_1HW_P string, T5_1CC_P string, T5_1HWC_P string, T5_1CCC_P string, T5_1FC_P string, T5_1MC_P string, T5_1CO_P string, T5_1CCO_P string, T5_1FCO_P string, T5_1MCO_P string, T5_1GETFU_P string, T5_1NHR_P string, T5_1GENP_P string, T5_1T_P string,
      T5_2_1PH string, T5_2_2PH string, T5_2_3PH string, T5_2_4PH string, T5_2_5PH string, T5_2_6PH string, T5_2_7PH string, T5_2_GE8H string, T5_2_TH string, T5_2_1PP string, T5_2_2PP string, T5_2_3PP string, T5_2_4PP string, T5_2_5PP string, T5_2_6PP string, T5_2_7PP string, T5_2_GE8P string, T5_2_TP string, T6_1_HB_H string, T6_1_FA_H string, T6_1_BS_H string, T6_1_CM_H string, T6_1_NS_H string, T6_1_TH string, T6_1_HB_P string, T6_1_FA_P string, T6_1_BS_P string, T6_1_CM_P string, T6_1_NS_P string, T6_1_TP string,
      T6_2_PRE19H string, T6_2_19_45H string, T6_2_46_60H string, T6_2_61_70H string, T6_2_71_80H string, T6_2_81_90H string, T6_2_91_00H string, T6_2_01_05H string, T6_2_06LH string, T6_2_NSH string, T6_2_TH string, T6_2_PRE19P string, T6_2_19_45P string, T6_2_46_60P string, T6_2_61_70P string, T6_2_71_80P string, T6_2_81_90P string, T6_2_91_00P string, T6_2_01_05P string, T6_2_06LP string, T6_2_NSP string, T6_2_TP string, T6_3_OOMH string, T6_3_OCNMH string, T6_3_RPLH string, T6_3_RLAH string, T6_3_RVBH string, T6_3_OFRH string, T6_3_NSH string, T6_3_TH string,
      T6_3_OOMP string, T6_3_OCNMP string, T6_3_RPLP string, T6_3_RLAP string, T6_3_RVBP string, T6_3_OFRP string, T6_3_NSP string, T6_3_TP string, T6_4_1RH string, T6_4_2RH string, T6_4_3RH string, T6_4_4RH string, T6_4_5RH string, T6_4_6RH string, T6_4_7RH string, T6_4_GE8RH string, T6_4_NSH string, T6_4_TH string, T6_4_1RP string, T6_4_2RP string, T6_4_3RP string, T6_4_4RP string, T6_4_5RP string, T6_4_6RP string, T6_4_7RP string, T6_4_GE8RP string, T6_4_NSP string, T6_4_TP string, T6_5_NCH string, T6_5_OCH string,
      T6_5_NGCH string, T6_5_ECH string, T6_5_CCH string, T6_5_PCH string, T6_5_LPGCH string, T6_5_WCH string, T6_5_OTH string, T6_5_NS string, T6_5_T string, T6_6_PM string, T6_6_GSLA string, T6_6_GSP string, T6_6_OP string, T6_6_N string, T6_6_NS string, T6_6_T string, T6_7_PS string, T6_7_IST string, T6_7_OIT string, T6_7_OTH string, T6_7_NSF string, T6_7_NS string, T6_7_T string, T6_8_O string, T6_8_U string, T6_8_T string, T7_1_NE string, T7_1_NP string, T8_1_WM string, T8_1_LFFJM string,
      T8_1_ULGUPJM string, T8_1_SM string, T8_1_LAHFM string, T8_1_RM string, T8_1_UTWSDM string, T8_1_OTHM string, T8_1_TM string, T8_1_WF string, T8_1_LFFJF string, T8_1_ULGUPJF string, T8_1_SF string, T8_1_LAHFF string, T8_1_RF string, T8_1_UTWSDF string, T8_1_OTHF string, T8_1_TF string, T8_1_WT string, T8_1_LFFJT string, T8_1_ULGUPJT string, T8_1_ST string, T8_1_LAHFT string, T8_1_RT string, T8_1_UTWSDT string, T8_1_OTHT string, T8_1_TT string, T9_1_PWM string, T9_1_MTM string, T9_1_NMM string, T9_1_SM string, T9_1_SSM string,
      T9_1_USM string, T9_1_OTHGEUM string, T9_1_TM string, T9_1_PWF string, T9_1_MTF string, T9_1_NMF string, T9_1_SF string, T9_1_SSF string, T9_1_USF string, T9_1_OTHGEUF string, T9_1_TF string, T9_1_PWT string, T9_1_MTT string, T9_1_NMT string, T9_1_ST string, T9_1_SST string, T9_1_UST string, T9_1_OTHGEUT string, T9_1_TT string, T9_2_HA string, T9_2_HB string, T9_2_HC string, T9_2_HD string, T9_2_HE string, T9_2_HF string, T9_2_HG string, T9_2_HH string, T9_2_HI string, T9_2_HJ string, T9_2_HZ string,
      T9_2_HT string, T9_2_PA string, T9_2_PB string, T9_2_PC string, T9_2_PD string, T9_2_PE string, T9_2_PF string, T9_2_PG string, T9_2_PH string, T9_2_PI string, T9_2_PJ string, T9_2_PZ string, T9_2_PT string, T10_1_LT15M string, T10_1_15M string, T10_1_16M string, T10_1_17M string, T10_1_18M string, T10_1_19M string, T10_1_20M string, T10_1_GE21M string, T10_1_NSM string, T10_1_TM string, T10_1_LT15F string, T10_1_15F string, T10_1_16F string, T10_1_17F string, T10_1_18F string, T10_1_19F string, T10_1_20F string,
      T10_1_GE21F string, T10_1_NSF string, T10_1_TF string, T10_1_LT15T string, T10_1_15T string, T10_1_16T string, T10_1_17T string, T10_1_18T string, T10_1_19T string, T10_1_20T string, T10_1_GE21T string, T10_1_NST string, T10_1_TT string, T10_2_SASM string, T10_2_OTHM string, T10_2_SASF string, T10_2_OTHF string, T10_2_SAST string, T10_2_OTHT string, T10_3_EDUM string, T10_3_ARTM string, T10_3_HUMM string, T10_3_SOCM string, T10_3_SCIM string, T10_3_ENGM string, T10_3_AGRM string, T10_3_HEAM string, T10_3_SERM string, T10_3_OTHM string, T10_3_NSM string,
      T10_3_TM string, T10_3_EDUF string, T10_3_ARTF string, T10_3_HUMF string, T10_3_SOCF string, T10_3_SCIF string, T10_3_ENGF string, T10_3_AGRF string, T10_3_HEAF string, T10_3_SERF string, T10_3_OTHF string, T10_3_NSF string, T10_3_TF string, T10_3_EDUT string, T10_3_ARTT string, T10_3_HUMT string, T10_3_SOCT string, T10_3_SCIT string, T10_3_ENGT string, T10_3_AGRT string, T10_3_HEAT string, T10_3_SERT string, T10_3_OTHT string, T10_3_NST string, T10_3_TT string, T10_4_NFM string, T10_4_PM string, T10_4_LSM string, T10_4_USM string, T10_4_TVM string,
      T10_4_ACCAM string, T10_4_HCM string, T10_4_ODNDM string, T10_4_HDPQM string, T10_4_PDM string, T10_4_DM string, T10_4_NSM string, T10_4_TM string, T10_4_NFF string, T10_4_PF string, T10_4_LSF string, T10_4_USF string, T10_4_TVF string, T10_4_ACCAF string, T10_4_HCF string, T10_4_ODNDF string, T10_4_HDPQF string, T10_4_PDF string, T10_4_DF string, T10_4_NSF string, T10_4_TF string, T10_4_NFT string, T10_4_PT string, T10_4_LST string, T10_4_UST string, T10_4_TVT string, T10_4_ACCAT string, T10_4_HCT string, T10_4_ODNDT string, T10_4_HDPQT string,
      T10_4_PDT string, T10_4_DT string, T10_4_NST string, T10_4_TT string, T11_1_F string, T11_1_BI string, T11_1_BU string, T11_1_TDL string, T11_1_M string, T11_1_CD string, T11_1_CP string, T11_1_V string, T11_1_OTH string, T11_1_NS string, T11_1_T string, T11_2_T1 string, T11_2_T2 string, T11_2_T3 string, T11_2_T4 string, T11_2_T5 string, T11_2_T6 string, T11_2_T7 string, T11_2_T8 string, T11_2_NS string, T11_2_T string, T11_3_D1 string, T11_3_D2 string, T11_3_D3 string, T11_3_D4 string, T11_3_D5 string,
      T11_3_D6 string, T11_3_NS string, T11_3_T string, T12_1AGE0_14 string, T12_1AGE15_24 string, T12_1AGE25_44 string, T12_1AGE45_64 string, T12_1AGEGE65 string, T12_1AGET string, T12_21_14M string, T12_215_28M string, T12_229_42M string, T12_2GE43M string, T12_2NSM string, T12_2TM string, T12_21_14F string, T12_215_28F string, T12_229_42F string, T12_2GE43F string, T12_2NSF string, T12_2TF string, T12_3VGM string, T12_3GM string, T12_3FM string, T12_3BM string, T12_3VBM string, T12_3NSM string, T12_3TM string, T12_3VGF string, T12_3GF string,
      T12_3FF string, T12_3BF string, T12_3VBF string, T12_3NSF string, T12_3TF string, T12_3VGT string, T12_3GT string, T12_3FT string, T12_3BT string, T12_3VBT string, T12_3NST string, T12_3TT string, T13_1_MDSOM string, T13_1_POM string, T13_1_APTOM string, T13_1_ASOM string, T13_1_STOM string, T13_1_CLOSOM string, T13_1_SCSOM string, T13_1_PPMOM string, T13_1_EOM string, T13_1_NSM string, T13_1_TM string, T13_1_MDSOF string, T13_1_POF string, T13_1_APTOF string, T13_1_ASOF string, T13_1_STOF string, T13_1_CLOSOF string, T13_1_SCSOF string,
      T13_1_PPMOF string, T13_1_EOF string, T13_1_NSF string, T13_1_TF string, T13_1_MDSOT string, T13_1_POT string, T13_1_APTOT string, T13_1_ASOT string, T13_1_STOT string, T13_1_CLOSOT string, T13_1_SCSOT string, T13_1_PPMOT string, T13_1_EOT string, T13_1_NST string, T13_1_TT string, T14_1_AFFM string, T14_1_BCM string, T14_1_MIM string, T14_1_CTM string, T14_1_TCM string, T14_1_PAM string, T14_1_PSM string, T14_1_OTHM string, T14_1_TM string, T14_1_AFFF string, T14_1_BCF string, T14_1_MIF string, T14_1_CTF string, T14_1_TCF string, T14_1_PAF string,
      T14_1_PSF string, T14_1_OTHF string, T14_1_TF string, T15_1_NC string, T15_1_1C string, T15_1_2C string, T15_1_3C string, T15_1_GE4C string, T15_2_Y string, T15_2_N string, T15_2_NS string, T15_2_T string, T15_3_B string, T15_3_OTH string, T15_3_N string, T15_3_NS string, T15_3_T string
    -> ExpressionEvaluator_19

Bookmark: Reproject Data
Note: Reprojector Parameters: / 1. Destination Coordinate System = EPSG:2157
Reprojector_2
    DEST = EPSG:2157
    INTERPOLATION_TYPE_NAME = Nearest Neighbor
    RASTER_CELL_SIZE = Preserve Cells
    RASTER_TOLERANCE = 0.0
    SOURCE = Read from feature
    REPROJECTED -> AreaCalculator_4

Bookmark: Calculate Area sq m
Note: Note: Area is approximate using generalised data
AreaCalculator_4
    AREA_ATTR = _area
    AREA_TYPE = Plane Area
    MULT = 1
    -> Clipper_3 [CLIPPEE]

Bookmark: Clip spatial data to boundary
Note: Clipper Parameters: / 1. Clippees on Clipper Boundary = Treat as Inside
Clipper_3
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> FeatureJoiner_2 [LEFT]

Bookmark: Attribute Processing
Note: Feature Joiner Parameters: / 1. Join on GUID
FeatureJoiner_2
    ATTR_CONFLICT_RES = Use Left
    GEOMETRY_HANDLING = Use Left
    JOIN_KEYS = GUID GUID AUTO
    JOIN_MODE = Inner
    JOINED -> ExpressionEvaluator
    JOINED -> Deaggregator

Bookmark: Remove Duplicate Shapes Created by Clipper for 3D
Note: Deaggregator Parameters: / 1. DEFAULT
Deaggregator
    ATTR_ACCUM_MODE = Merge List Attributes
    ATTR_CONFLICT_RES = Use List Attribute Values
    CHILD_ID_ATTR = _hierarchy_child_id_list
    COPY_ATTR = Every Node
    EXPLODE_INSTANCES = No
    GEOM_NAME_FIELD = _geometry_name
    ID_ATTR = _hierarchy_id
    ID_SELECTION = ID and Parent ID
    LIST_ATTR_MODE_LOOKUP = LEAN
    MODE = Flatten One Level
    PARENT_ID_ATTR = _hierarchy_parent_id
    PART_NUMBER_FIELD = _part_number
    SPLIT_COMPOSITES = No
    DEAGGREGATED -> AreaCalculator
Note: Area Calculator Parameters: / 1. Area attribute = _area
AreaCalculator
    AREA_ATTR = _area
    AREA_TYPE = Plane Area
    MULT = 1
    -> Sorter
Note: Sorter Parameters: / 1. Sort by = _area / Numeric / Descending
Note: NOTE: This is a workaround to remove multiple geometries with the same ID that are created by the processing of clipping when it separates two parts of the same geographic feature by removing their joing geometry. This process simply removes the smaller of the the parts. A preferred solution would be to merge the resulting geomtries and flattern the hierarchy prior to export as FBX.
Sorter
    SORT_PARM = _area NUMERIC DESCENDING
    SORTED -> DuplicateFilter
Note: Duplicate Filter Parameters: / 1. Key Attributes = GUID
DuplicateFilter
    INPUT_ORDERED_CHOICE = No
    KEYATTR = GUID
    UNIQUE -> 3DForcer_3

Bookmark: Convert 2D polygons to 3D objects
3DForcer_3
    KEEPZVAL = No
    ZVALATTR = 0
    -> Extruder_3
Note: 3D Forcer Parameters: / 1. Elevation = 0
Note: Extruder Parameters: / 1. Direction = Vertical / 2. Distance = 1 (metres)
Extruder_3
    DIRECTION = Vertical
    DISTANCE = 1
    EXTRUDED -> GeometryPropertySetter_3
Note: Geometry Property Setter Parameters: / 1. Property to Set = Geometry Name / 2. Geometry Name = GUID
GeometryPropertySetter_3
    GEOM_NAME_FIELD = @Value(GUID)
    OVERWRITE_CHOICE = Yes
    SETTYPE_PARAM = Geometry Name
    SET -> SAPS_2016 (writer FBX_3)

Bookmark: File Outputs
Note: FBX Writer Parameters: / 1. SET OUTPUT FILE LOCATION / 2. Coordinate System = EPSG:2157 / 3. Move to Local Coordinate System = No
SAPS_2016 (writer FBX_3)
Note: CSV Writer Parameters: / 1. SET OUTPUT FILE LOCATION / 2. Specify feilds to output
SAPS_2016 (writer CSV2_11)
    attributes: GUID string, NUTS1 string, NUTS1NAME string, NUTS2 string, NUTS2NAME string, NUTS3 string, NUTS3NAME string, COUNTY string, COUNTYNAME string, CSOED string, OSIED string, EDNAME string, SA_PUB2011 string, SMALL_AREA string, GEOGID string, GEOGDESC string, TO_POP2016 string, TO_HOU2016 string, AREA_SQMET string, POP_DENS string, DEP_RATIO string, PER_NONIRE string, HO_PRE2001 string, HO_POS2001 string, PER_FLAPBE string, PER_RENT string, PER_VAC string, PER_UNEM string, PER_PROF string, PER_O_OCC string,
      PER_3ED string, PER_NO3ED string, AV_PER_HOU string, PER_NO_INT string, PER_DISAB string, TO_POP2011 string, PER_CH_POP string, TO_HOU2011 string, PER_CH_HOU string
Note: JSON Writer Parameters: / 1. SET OUTPUT FILE LOCATION / 2. Specify fields to output
SAPS_2016 (writer JSON_1)
    attributes: GUID string, NUTS1 string, NUTS1NAME string, NUTS2 string, NUTS2NAME string, NUTS3 string, NUTS3NAME string, COUNTY string, COUNTYNAME string, CSOED string, OSIED string, EDNAME string, SA_PUB2011 string, SMALL_AREA string, GEOGID string, GEOGDESC string, TO_POP2016 string, TO_HOU2016 string, AREA_SQMET string, POP_DENS string, DEP_RATIO string, PER_NONIRE string, HO_PRE2001 string, HO_POS2001 string, PER_FLAPBE string, PER_RENT string, PER_VAC string, PER_UNEM string, PER_PROF string, PER_O_OCC string,
      PER_3ED string, PER_NO3ED string, AV_PER_HOU string, PER_NO_INT string, PER_DISAB string, TO_POP2011 string, PER_CH_POP string, TO_HOU2011 string, PER_CH_HOU string
Note: Shapefile Writer Parameters: / 1. SET OUTPUT FILE LOCATION / 2. Specify fields to output / 3. SET OUTPUT DATA TYPES
SAPS_2016 (writer ESRISHAPE_9)
    attributes: GUID char(80), NUTS1 char(80), NUTS1NAME char(80), NUTS2 char(80), NUTS2NAME char(80), NUTS3 char(80), NUTS3NAME char(80), COUNTY char(80), COUNTYNAME char(80), CSOED char(80), OSIED char(80), EDNAME char(80), SA_PUB2011 char(80), SMALL_AREA char(80), GEOGID char(80), GEOGDESC char(254), TO_POP2016 number(200,10), TO_HOU2016 number(200,10), AREA_SQMET double, POP_DENS float, DEP_RATIO float, PER_NONIRE float, HO_PRE2001 number(20,10), HO_POS2001 number(20,10), PER_FLAPBE float, PER_RENT float, PER_VAC float, PER_UNEM float, PER_PROF float, PER_O_OCC float,
      PER_3ED float, PER_NO3ED float, AV_PER_HOU float, PER_NO_INT float, PER_DISAB float, TO_POP2011 number(200,10), PER_CH_POP float, TO_HOU2011 number(200,10), PER_CH_HOU float
Note: Atrribute Name Writer Parameters: / 1. SET OUTPUT FILE LOCATION / 2. Specify fields to output
SAPS_2016_Attribute_Names (writer CSV2_13)
    attributes: Attribute_Name string, Display_Name string

Bookmark: Population Density sq km
ExpressionEvaluator
    ACTION = Create New Attribute
    EXPRESSION = @round((@Value(T1_1AGETT) / @Value(_area)) * 1000000,2)
    VAL_ATTR = Pop_Density
    -> ExpressionEvaluator_2

Bookmark: Dependents (per 100)
ExpressionEvaluator_2
    ACTION = Create New Attribute
    EXPRESSION = @round((@sum(@Value(T1_1AGE0T),@Value(T1_1AGE1T),@Value(T1_1AGE2T),@Value(T1_1AGE3T),@Value(T1_1AGE4T),@Value(T1_1AGE5T),@Value(T1_1AGE6T),@Value(T1_1AGE7T),@Value(T1_1AGE8T),@Value(T1_1AGE9T),@Value(T1_1AGE10T),@Value(T1_1AGE11T),@Value(T1_1AGE12T),@Value(T1_1AGE13T),@Value(T1_1AGE14T),@Value(T1_1AGE65_69T),@Value(T1_1AGE70_74T),@Value(T1_1AGE75_79T),@Value(T1_1AGE80_84T),@Value(T1_1AGEGE_85T))) / (@sum(@Value(T1_1AGE15T),@Value(T1_1AGE16T),@Value(T1_1AGE17T),@Value(T1_1AGE18T),@Value(T1_1AGE19T),@Value(T1_1AGE20_24T),@Value(T1_1AGE25_29T),@Value(T1_1AGE30_34T),@Value(T1_1AGE35_39T),@Value(T1_1AGE40_44T),@Value(T1_1AGE45_49T),@Value(T1_1AGE50_54T),@Value(T1_1AGE55_59T),@Value(T1_1AGE60_64T))) * 100,2)
    VAL_ATTR = Dep_Ratio
    -> ExpressionEvaluator_3

Bookmark: Percentage non-Irish Nationals
ExpressionEvaluator_3
    ACTION = Create New Attribute
    EXPRESSION = @round(((@Value(T2_1TN) - @Value(T2_1IEN)) / @Value(T2_1TN)) * 100,2)
    VAL_ATTR = Percent_NonIrish
    -> ExpressionEvaluator_4

Bookmark: Households Built pre 2001
ExpressionEvaluator_4
    ACTION = Create New Attribute
    EXPRESSION = @sum(@Value(T6_2_PRE19H),@Value(T6_2_19_45H),@Value(T6_2_46_60H),@Value(T6_2_61_70H),@Value(T6_2_71_80H),@Value(T6_2_81_90H),@Value(T6_2_91_00H))
    VAL_ATTR = HouseBuilt_Pre2001
    -> ExpressionEvaluator_5

Bookmark: Households Built 2001+
ExpressionEvaluator_5
    ACTION = Create New Attribute
    EXPRESSION = @sum(@Value(T6_2_01_10H),@Value(T6_2_11LH))
    VAL_ATTR = HouseBuilt_Post2001
    -> ExpressionEvaluator_6

Bookmark: Percentage Flats / Apart / Bedsit
ExpressionEvaluator_6
    ACTION = Create New Attribute
    EXPRESSION = @round((@sum(@Value(T6_1_FA_H),@Value(T6_1_BS_H)) / @Value(T6_1_TH)) * 100,2)
    VAL_ATTR = Percent_FlatApartBedsit
    -> ExpressionEvaluator_7

Bookmark: Percentage Rented Households
ExpressionEvaluator_7
    ACTION = Create New Attribute
    EXPRESSION = @round((@sum(@Value(T6_3_RPLH),@Value(T6_3_RLAH),@Value(T6_3_RVCHBH)) / @Value(T6_3_TH)) * 100,2)
    VAL_ATTR = Percent_Rented
    -> ExpressionEvaluator_8

Bookmark: Percentage Vacant Households
ExpressionEvaluator_8
    ACTION = Create New Attribute
    EXPRESSION = @round((@sum(@Value(T6_8_TA),@Value(T6_8_OVD)) / @Value(T6_8_T)) * 100,2)
    VAL_ATTR = Percent_Vacant
    -> ExpressionEvaluator_9

Bookmark: Percentage Unemployed
ExpressionEvaluator_9
    ACTION = Create New Attribute
    EXPRESSION = @round((@Value(T8_1_ULGUPJT) / @Value(T8_1_TT)) * 100,2)
    VAL_ATTR = Percent_Unemployed
    -> ExpressionEvaluator_10

Bookmark: Percentage Social Class A/B
ExpressionEvaluator_10
    ACTION = Create New Attribute
    EXPRESSION = @round((@sum(@Value(T9_2_HA),@Value(T9_2_HB)) / @Value(T9_2_HT)) * 100,2)
    VAL_ATTR = Percent_Professional
    -> ExpressionEvaluator_11

Bookmark: Percentage Social Class Other
ExpressionEvaluator_11
    ACTION = Create New Attribute
    EXPRESSION = @round((@sum(@Value(T9_2_HC),@Value(T9_2_HD),@Value(T9_2_HE),@Value(T9_2_HF),@Value(T9_2_HG),@Value(T9_2_HH),@Value(T9_2_HI),@Value(T9_2_HJ),@Value(T9_2_HZ)) / @Value(T9_2_HT)) * 100,2)
    VAL_ATTR = Percent_OtherOccupation
    -> ExpressionEvaluator_12

Bookmark: Percentage Third Level Edu
ExpressionEvaluator_12
    ACTION = Create New Attribute
    EXPRESSION = @round(@sum(@Value(T10_4_ODNDT),@Value(T10_4_HDPQT),@Value(T10_4_PDT),@Value(T10_4_DT)) / @Value(T10_4_TT) * 100,2)
    VAL_ATTR = Percent_ThirdLevelEdu
    -> ExpressionEvaluator_13

Bookmark: Percentage No Second Level Edu
ExpressionEvaluator_13
    ACTION = Create New Attribute
    EXPRESSION = @round(@sum(@Value(T10_4_NFT),@Value(T10_4_PT),@Value(T10_4_LST),@Value(T10_4_UST),@Value(T10_4_NST)) / @Value(T10_4_TT) * 100,2)
    VAL_ATTR = Percent_NoThirdLevelEdu
    -> ExpressionEvaluator_14

Bookmark: Average Persons per Household
ExpressionEvaluator_14
    ACTION = Create New Attribute
    EXPRESSION = @round(@Value(T5_2_TP) / @Value(T5_2_TH),2)
    VAL_ATTR = Average_PersonsPerHousehold
    -> ExpressionEvaluator_16

Bookmark: Percentage of homes without internet
ExpressionEvaluator_16
    ACTION = Create New Attribute
    EXPRESSION = @round((@Value(T15_3_NS) / @Value(T15_3_T))  * 100,2)
    VAL_ATTR = Percent_NoInternet
    -> ExpressionEvaluator_17

Bookmark: Percentage of Persons with a Disability
ExpressionEvaluator_17
    ACTION = Create New Attribute
    EXPRESSION = @round((@Value(T12_1_T) / @Value(T1_1AGETT))  * 100,2)
    VAL_ATTR = Percent_WithDisability
    -> FeatureJoiner_3 [LEFT]

Bookmark: Select Attributes from 2011 Census for Comparison
Note: Expression Calculator Parameters: / 1. Select Total Households attribute (T5_1T_H) / 2. Output as TotalHouse2011
ExpressionEvaluator_19
    ACTION = Create New Attribute
    EXPRESSION = @Value(T5_1T_H)
    VAL_ATTR = TotalHouse2011
    -> ExpressionEvaluator_18
Note: Expression Calculator Parameters: / 1. Select Total Population attribute (T1_AGETT) / 2. Output as TotalPop2011
ExpressionEvaluator_18
    ACTION = Create New Attribute
    EXPRESSION = @Value(T1_1AGETT)
    VAL_ATTR = TotalPop2011
    -> AttributeKeeper
Note: Attribute Keeper Parameters: / 1. Select GEOGID TotalPop2011 and TotalHouse2011
AttributeKeeper
    KEEP_ATTRS = TotalPop2011,GEOGID,TotalHouse2011
    -> FeatureJoiner_3 [RIGHT]
Note: Feature Joiner Parameters: / 1. Join on GEOGID
FeatureJoiner_3
    ATTR_CONFLICT_RES = Use Left
    GEOMETRY_HANDLING = Use Left
    JOIN_KEYS = GEOGID GEOGID AUTO
    JOIN_MODE = Inner
    JOINED -> ExpressionEvaluator_15

Bookmark: Percentage Change of Population 2011 - 2016
ExpressionEvaluator_15
    ACTION = Create New Attribute
    EXPRESSION = @round(((@Value(T1_1AGETT) - @Value(TotalPop2011)) / @Value(TotalPop2011)) * 100,2)
    VAL_ATTR = Percent_ChangePopulation
    -> ExpressionEvaluator_20

Bookmark: Percentage Change of Households 2011 - 2016
ExpressionEvaluator_20
    ACTION = Create New Attribute
    EXPRESSION = @round(((@Value(T5_1T_H) - @Value(TotalHouse2011)) / @Value(TotalHouse2011)) * 100,2)
    VAL_ATTR = Percent_ChangeHouseholds
    -> AttributeManager

Bookmark: Select Output Attributes
Note: Parameters: / 1. Remove unnecessary attributes / 2. Renamed Attributes to 10 chars for consistency with Shapefile outputs.
AttributeManager
    ATTR_TABLE:
      REMOVE OBJECTID
      REMOVE AREA
      REMOVE CHANGECODE
      REMOVE ESRI_OID
      REMOVE Shape__Are
      REMOVE Shape__Len
      REMOVE _clipped
      REMOVE T1_1AGE0M
      REMOVE T1_1AGE1M
      REMOVE T1_1AGE2M
      REMOVE T1_1AGE3M
      REMOVE T1_1AGE4M
      REMOVE T1_1AGE5M
      REMOVE T1_1AGE6M
      REMOVE T1_1AGE7M
      REMOVE T1_1AGE8M
      REMOVE T1_1AGE9M
      REMOVE T1_1AGE10M
      REMOVE T1_1AGE11M
      REMOVE T1_1AGE12M
      REMOVE T1_1AGE13M
      REMOVE T1_1AGE14M
      REMOVE T1_1AGE15M
      REMOVE T1_1AGE16M
      REMOVE T1_1AGE17M
      REMOVE T1_1AGE18M
      REMOVE T1_1AGE19M
      REMOVE T1_1AGE20_24M
      REMOVE T1_1AGE25_29M
      REMOVE T1_1AGE30_34M
      REMOVE T1_1AGE35_39M
      REMOVE T1_1AGE40_44M
      REMOVE T1_1AGE45_49M
      REMOVE T1_1AGE50_54M
      REMOVE T1_1AGE55_59M
      REMOVE T1_1AGE60_64M
      REMOVE T1_1AGE65_69M
      REMOVE T1_1AGE70_74M
      REMOVE T1_1AGE75_79M
      REMOVE T1_1AGE80_84M
      REMOVE T1_1AGEGE_85M
      REMOVE T1_1AGETM
      REMOVE T1_1AGE0F
      REMOVE T1_1AGE1F
      REMOVE T1_1AGE2F
      REMOVE T1_1AGE3F
      REMOVE T1_1AGE4F
      REMOVE T1_1AGE5F
      REMOVE T1_1AGE6F
      REMOVE T1_1AGE7F
      REMOVE T1_1AGE8F
      REMOVE T1_1AGE9F
      REMOVE T1_1AGE10F
      REMOVE T1_1AGE11F
      REMOVE T1_1AGE12F
      REMOVE T1_1AGE13F
      REMOVE T1_1AGE14F
      REMOVE T1_1AGE15F
      REMOVE T1_1AGE16F
      REMOVE T1_1AGE17F
      REMOVE T1_1AGE18F
      REMOVE T1_1AGE19F
      REMOVE T1_1AGE20_24F
      REMOVE T1_1AGE25_29F
      REMOVE T1_1AGE30_34F
      REMOVE T1_1AGE35_39F
      REMOVE T1_1AGE40_44F
      REMOVE T1_1AGE45_49F
      REMOVE T1_1AGE50_54F
      REMOVE T1_1AGE55_59F
      REMOVE T1_1AGE60_64F
      REMOVE T1_1AGE65_69F
      REMOVE T1_1AGE70_74F
      REMOVE T1_1AGE75_79F
      REMOVE T1_1AGE80_84F
      REMOVE T1_1AGEGE_85F
      REMOVE T1_1AGETF
      REMOVE T1_1AGE0T
      REMOVE T1_1AGE1T
      REMOVE T1_1AGE2T
      REMOVE T1_1AGE3T
      REMOVE T1_1AGE4T
      REMOVE T1_1AGE5T
      REMOVE T1_1AGE6T
      REMOVE T1_1AGE7T
      REMOVE T1_1AGE8T
      REMOVE T1_1AGE9T
      REMOVE T1_1AGE10T
      REMOVE T1_1AGE11T
      REMOVE T1_1AGE12T
      REMOVE T1_1AGE13T
      REMOVE T1_1AGE14T
      REMOVE T1_1AGE15T
      REMOVE T1_1AGE16T
      REMOVE T1_1AGE17T
      REMOVE T1_1AGE18T
      REMOVE T1_1AGE19T
      REMOVE T1_1AGE20_24T
      REMOVE T1_1AGE25_29T
      REMOVE T1_1AGE30_34T
      REMOVE T1_1AGE35_39T
      REMOVE T1_1AGE40_44T
      REMOVE T1_1AGE45_49T
      REMOVE T1_1AGE50_54T
      REMOVE T1_1AGE55_59T
      REMOVE T1_1AGE60_64T
      REMOVE T1_1AGE65_69T
      REMOVE T1_1AGE70_74T
      REMOVE T1_1AGE75_79T
      REMOVE T1_1AGE80_84T
      REMOVE T1_1AGEGE_85T
      RENAME_SET_VALUE T1_1AGETT > TO_POP2016
      REMOVE T1_2SGLM
      REMOVE T1_2MARM
      REMOVE T1_2SEPM
      REMOVE T1_2DIVM
      REMOVE T1_2WIDM
      REMOVE T1_2TM
      REMOVE T1_2SGLF
      REMOVE T1_2MARF
      REMOVE T1_2SEPF
      REMOVE T1_2DIVF
      REMOVE T1_2WIDF
      REMOVE T1_2TF
      REMOVE T1_2SGLT
      REMOVE T1_2MART
      REMOVE T1_2SEPT
      REMOVE T1_2DIVT
      REMOVE T1_2WIDT
      REMOVE T1_2T
      REMOVE T2_1IEBP
      REMOVE T2_1UKBP
      REMOVE T2_1PLBP
      REMOVE T2_1LTBP
      REMOVE T2_1EUBP
      REMOVE T2_1RWBP
      REMOVE T2_1TBP
      REMOVE T2_1IEN
      REMOVE T2_1UKN
      REMOVE T2_1PLN
      REMOVE T2_1LTN
      REMOVE T2_1EUN
      REMOVE T2_1RWN
      REMOVE T2_1NSN
      REMOVE T2_1TN
      REMOVE T2_2WI
      REMOVE T2_2WIT
      REMOVE T2_2OW
      REMOVE T2_2BBI
      REMOVE T2_2AAI
      REMOVE T2_2OTH
      REMOVE T2_2NS
      REMOVE T2_2T
      REMOVE T2_3SA
      REMOVE T2_3EC
      REMOVE T2_3EI
      REMOVE T2_3OI
      REMOVE T2_3T
      REMOVE T2_4CA
      REMOVE T2_4OR
      REMOVE T2_4NR
      REMOVE T2_4NS
      REMOVE T2_4T
      REMOVE T2_5PL
      REMOVE T2_5FR
      REMOVE T2_5LT
      REMOVE T2_5OTH
      REMOVE T2_5T
      REMOVE T2_6VW
      REMOVE T2_6W
      REMOVE T2_6NW
      REMOVE T2_6NAA
      REMOVE T2_6NS
      REMOVE T2_6T
      REMOVE T3_1YES
      REMOVE T3_1NO
      REMOVE T3_1NS
      REMOVE T3_1T
      REMOVE T3_2DIM
      REMOVE T3_2DIDOM
      REMOVE T3_2DIWOM
      REMOVE T3_2DILOOM
      REMOVE T3_2DINOM
      REMOVE T3_2DOESM
      REMOVE T3_2WOESM
      REMOVE T3_2LOOESM
      REMOVE T3_2NOESM
      REMOVE T3_2NSM
      REMOVE T3_2ALLM
      REMOVE T3_2DIF
      REMOVE T3_2DIDOF
      REMOVE T3_2DIWOF
      REMOVE T3_2DILOOF
      REMOVE T3_2DINOF
      REMOVE T3_2DOESF
      REMOVE T3_2WOESF
      REMOVE T3_2LOOESF
      REMOVE T3_2NOESF
      REMOVE T3_2NSF
      REMOVE T3_2ALLF
      REMOVE T3_2DIT
      REMOVE T3_2DIDOT
      REMOVE T3_2DIWOT
      REMOVE T3_2DILOOT
      REMOVE T3_2DINOT
      REMOVE T3_2DOEST
      REMOVE T3_2WOEST
      REMOVE T3_2LOOEST
      REMOVE T3_2NOEST
      REMOVE T3_2NST
      REMOVE T3_2ALLT
      REMOVE T4_1_2PF
      REMOVE T4_1_3PF
      REMOVE T4_1_4PF
      REMOVE T4_1_5PF
      REMOVE T4_1_GRE_6PF
      REMOVE T4_1_TF
      REMOVE T4_1_2PP
      REMOVE T4_1_3PP
      REMOVE T4_1_4PP
      REMOVE T4_1_5PP
      REMOVE T4_1_GRE_6PP
      REMOVE T4_1_TP
      REMOVE T4_1_2PC
      REMOVE T4_1_3PC
      REMOVE T4_1_4PC
      REMOVE T4_1_5PC
      REMOVE T4_1_GRE_6PC
      REMOVE T4_1_TC
      REMOVE T4_2_1CU15
      REMOVE T4_2_2CU15
      REMOVE T4_2_3CU15
      REMOVE T4_2_4CU15
      REMOVE T4_2_GE5CU15
      REMOVE T4_2_TCU15
      REMOVE T4_2_1CO15
      REMOVE T4_2_2CO15
      REMOVE T4_2_3CO15
      REMOVE T4_2_4CO15
      REMOVE T4_2_GE5CO15
      REMOVE T4_2_TCO15
      REMOVE T4_2_2CUO15
      REMOVE T4_2_3CUO15
      REMOVE T4_2_4CUO15
      REMOVE T4_2_GE5CUO15
      REMOVE T4_2_TCUO15
      REMOVE T4_2_NCT
      REMOVE T4_2_1CT
      REMOVE T4_2_2CT
      REMOVE T4_2_3CT
      REMOVE T4_2_4CT
      REMOVE T4_2_GE5CT
      REMOVE T4_2_TCT
      REMOVE T4_3FCCU15
      REMOVE T4_3FCCO15
      REMOVE T4_3FCCUO15
      REMOVE T4_3FCCT
      REMOVE T4_3FOPMCU15
      REMOVE T4_3FOPMCO15
      REMOVE T4_3FOPMCUO15
      REMOVE T4_3FOPMCT
      REMOVE T4_3FOPFCU15
      REMOVE T4_3FOPFCO15
      REMOVE T4_3FOPFCUO15
      REMOVE T4_3FOPFCT
      REMOVE T4_3CCCU15
      REMOVE T4_3CCCO15
      REMOVE T4_3CCCUO15
      REMOVE T4_3CCCT
      REMOVE T4_3COPMCU15
      REMOVE T4_3COPMCO15
      REMOVE T4_3COPMCUO15
      REMOVE T4_3COPMCT
      REMOVE T4_3COPFCU15
      REMOVE T4_3COPFCO15
      REMOVE T4_3COPFCUO15
      REMOVE T4_3COPFCT
      REMOVE T4_4AGE0_4F
      REMOVE T4_4AGE5_9F
      REMOVE T4_4AGE10_14F
      REMOVE T4_4AGE15_19F
      REMOVE T4_4AGE_GE20F
      REMOVE T4_4TF
      REMOVE T4_4AGE0_4P
      REMOVE T4_4AGE5_9P
      REMOVE T4_4AGE10_14P
      REMOVE T4_4AGE15_19P
      REMOVE T4_4AGE_GE20P
      REMOVE T4_4TP
      REMOVE T4_5PFF
      REMOVE T4_5ENF
      REMOVE T4_5RF
      REMOVE T4_5PSF
      REMOVE T4_5ESF
      REMOVE T4_5PAF
      REMOVE T4_5ADOF
      REMOVE T4_5ADUF
      REMOVE T4_5TF
      REMOVE T4_5PFP
      REMOVE T4_5ENP
      REMOVE T4_5RP
      REMOVE T4_5PSP
      REMOVE T4_5ESP
      REMOVE T4_5PAP
      REMOVE T4_5ADOP
      REMOVE T4_5ADUP
      REMOVE T4_5TP
      REMOVE T4_6_0C
      REMOVE T4_6_1C
      REMOVE T4_6_2C
      REMOVE T4_6_3C
      REMOVE T4_6_GE4C
      REMOVE T4_6T
      REMOVE T5_1OP_H
      REMOVE T5_1MC_H
      REMOVE T5_1CC_H
      REMOVE T5_1MCC_H
      REMOVE T5_1CCC_H
      REMOVE T5_1OPFC_H
      REMOVE T5_1OPMC_H
      REMOVE T5_1CO_H
      REMOVE T5_1CCO_H
      REMOVE T5_1OPFCO_H
      REMOVE T5_1OPMCO_H
      REMOVE T5_1GETFU_H
      REMOVE T5_1NHR_H
      REMOVE T5_1GENP_H
      RENAME_SET_VALUE T5_1T_H > TO_HOU2016
      REMOVE T5_1OP_P
      REMOVE T5_1MC_P
      REMOVE T5_1CC_P
      REMOVE T5_1MCC_P
      REMOVE T5_1CCC_P
      REMOVE T5_1OPFC_P
      REMOVE T5_1OPMC_P
      REMOVE T5_1CO_P
      REMOVE T5_1CCO_P
      REMOVE T5_1OPFCO_P
      REMOVE T5_1OPMCO_P
      REMOVE T5_1GETFU_P
      REMOVE T5_1NHR_P
      REMOVE T5_1GENP_P
      REMOVE T5_1T_P
      REMOVE T5_2_1PH
      REMOVE T5_2_2PH
      REMOVE T5_2_3PH
      REMOVE T5_2_4PH
      REMOVE T5_2_5PH
      REMOVE T5_2_6PH
      REMOVE T5_2_7PH
      REMOVE T5_2_GE8PH
      REMOVE T5_2_TH
      REMOVE T5_2_1PP
      REMOVE T5_2_2PP
      REMOVE T5_2_3PP
      REMOVE T5_2_4PP
      REMOVE T5_2_5PP
      REMOVE T5_2_6PP
      REMOVE T5_2_7PP
      REMOVE T5_2_GE8PP
      REMOVE T5_2_TP
      REMOVE T6_1_HB_H
      REMOVE T6_1_FA_H
      REMOVE T6_1_BS_H
      REMOVE T6_1_CM_H
      REMOVE T6_1_NS_H
      REMOVE T6_1_TH
      REMOVE T6_1_HB_P
      REMOVE T6_1_FA_P
      REMOVE T6_1_BS_P
      REMOVE T6_1_CM_P
      REMOVE T6_1_NS_P
      REMOVE T6_1_TP
      REMOVE T6_2_PRE19H
      REMOVE T6_2_19_45H
      REMOVE T6_2_46_60H
      REMOVE T6_2_61_70H
      REMOVE T6_2_71_80H
      REMOVE T6_2_81_90H
      REMOVE T6_2_91_00H
      REMOVE T6_2_01_10H
      REMOVE T6_2_11LH
      REMOVE T6_2_NSH
      REMOVE T6_2_TH
      REMOVE T6_2_PRE19P
      REMOVE T6_2_19_45P
      REMOVE T6_2_46_60P
      REMOVE T6_2_61_70P
      REMOVE T6_2_71_80P
      REMOVE T6_2_81_90P
      REMOVE T6_2_91_00P
      REMOVE T6_2_01_10P
      REMOVE T6_2_11LP
      REMOVE T6_2_NSP
      REMOVE T6_2_TP
      REMOVE T6_3_OMLH
      REMOVE T6_3_OOH
      REMOVE T6_3_RPLH
      REMOVE T6_3_RLAH
      REMOVE T6_3_RVCHBH
      REMOVE T6_3_OFRH
      REMOVE T6_3_NSH
      REMOVE T6_3_TH
      REMOVE T6_3_OMLP
      REMOVE T6_3_OOP
      REMOVE T6_3_RPLP
      REMOVE T6_3_RLAP
      REMOVE T6_3_RVCHBP
      REMOVE T6_3_OFRP
      REMOVE T6_3_NSP
      REMOVE T6_3_TP
      REMOVE T6_4_1RH
      REMOVE T6_4_2RH
      REMOVE T6_4_3RH
      REMOVE T6_4_4RH
      REMOVE T6_4_5RH
      REMOVE T6_4_6RH
      REMOVE T6_4_7RH
      REMOVE T6_4_GE8RH
      REMOVE T6_4_NSH
      REMOVE T6_4_TH
      REMOVE T6_4_1RP
      REMOVE T6_4_2RP
      REMOVE T6_4_3RP
      REMOVE T6_4_4RP
      REMOVE T6_4_5RP
      REMOVE T6_4_6RP
      REMOVE T6_4_7RP
      REMOVE T6_4_GE8RP
      REMOVE T6_4_NSP
      REMOVE T6_4_TP
      REMOVE T6_5_NCH
      REMOVE T6_5_OCH
      REMOVE T6_5_NGCH
      REMOVE T6_5_ECH
      REMOVE T6_5_CCH
      REMOVE T6_5_PCH
      REMOVE T6_5_LPGCH
      REMOVE T6_5_WCH
      REMOVE T6_5_OTH
      REMOVE T6_5_NS
      REMOVE T6_5_T
      REMOVE T6_6_PM
      REMOVE T6_6_GSLA
      REMOVE T6_6_GSP
      REMOVE T6_6_OP
      REMOVE T6_6_N
      REMOVE T6_6_NS
      REMOVE T6_6_T
      REMOVE T6_7_PS
      REMOVE T6_7_IST
      REMOVE T6_7_OIT
      REMOVE T6_7_OTH
      REMOVE T6_7_NSF
      REMOVE T6_7_NS
      REMOVE T6_7_T
      REMOVE T6_8_O
      REMOVE T6_8_TA
      REMOVE T6_8_UHH
      REMOVE T6_8_OVD
      REMOVE T6_8_T
      REMOVE T7_1_NE
      REMOVE T7_1_NP
      REMOVE T8_1_WM
      REMOVE T8_1_LFFJM
      REMOVE T8_1_ULGUPJM
      REMOVE T8_1_SM
      REMOVE T8_1_LAHFM
      REMOVE T8_1_RM
      REMOVE T8_1_UTWSDM
      REMOVE T8_1_OTHM
      REMOVE T8_1_TM
      REMOVE T8_1_WF
      REMOVE T8_1_LFFJF
      REMOVE T8_1_ULGUPJF
      REMOVE T8_1_SF
      REMOVE T8_1_LAHFF
      REMOVE T8_1_RF
      REMOVE T8_1_UTWSDF
      REMOVE T8_1_OTHF
      REMOVE T8_1_TF
      REMOVE T8_1_WT
      REMOVE T8_1_LFFJT
      REMOVE T8_1_ULGUPJT
      REMOVE T8_1_ST
      REMOVE T8_1_LAHFT
      REMOVE T8_1_RT
      REMOVE T8_1_UTWSDT
      REMOVE T8_1_OTHT
      REMOVE T8_1_TT
      REMOVE T9_1_PWM
      REMOVE T9_1_MTM
      REMOVE T9_1_NMM
      REMOVE T9_1_SM
      REMOVE T9_1_SSM
      REMOVE T9_1_USM
      REMOVE T9_1_OTHGEUM
      REMOVE T9_1_TM
      REMOVE T9_1_PWF
      REMOVE T9_1_MTF
      REMOVE T9_1_NMF
      REMOVE T9_1_SF
      REMOVE T9_1_SSF
      REMOVE T9_1_USF
      REMOVE T9_1_OTHGEUF
      REMOVE T9_1_TF
      REMOVE T9_1_PWT
      REMOVE T9_1_MTT
      REMOVE T9_1_NMT
      REMOVE T9_1_ST
      REMOVE T9_1_SST
      REMOVE T9_1_UST
      REMOVE T9_1_OTHGEUT
      REMOVE T9_1_TT
      REMOVE T9_2_HA
      REMOVE T9_2_HB
      REMOVE T9_2_HC
      REMOVE T9_2_HD
      REMOVE T9_2_HE
      REMOVE T9_2_HF
      REMOVE T9_2_HG
      REMOVE T9_2_HH
      REMOVE T9_2_HI
      REMOVE T9_2_HJ
      REMOVE T9_2_HZ
      REMOVE T9_2_HT
      REMOVE T9_2_PA
      REMOVE T9_2_PB
      REMOVE T9_2_PC
      REMOVE T9_2_PD
      REMOVE T9_2_PE
      REMOVE T9_2_PF
      REMOVE T9_2_PG
      REMOVE T9_2_PH
      REMOVE T9_2_PI
      REMOVE T9_2_PJ
      REMOVE T9_2_PZ
      REMOVE T9_2_PT
      REMOVE T10_1_LT15M
      REMOVE T10_1_15M
      REMOVE T10_1_16M
      REMOVE T10_1_17M
      REMOVE T10_1_18M
      REMOVE T10_1_19M
      REMOVE T10_1_20M
      REMOVE T10_1_GE21M
      REMOVE T10_1_NSM
      REMOVE T10_1_TM
      REMOVE T10_1_LT15F
      REMOVE T10_1_15F
      REMOVE T10_1_16F
      REMOVE T10_1_17F
      REMOVE T10_1_18F
      REMOVE T10_1_19F
      REMOVE T10_1_20F
      REMOVE T10_1_GE21F
      REMOVE T10_1_NSF
      REMOVE T10_1_TF
      REMOVE T10_1_LT15T
      REMOVE T10_1_15T
      REMOVE T10_1_16T
      REMOVE T10_1_17T
      REMOVE T10_1_18T
      REMOVE T10_1_19T
      REMOVE T10_1_20T
      REMOVE T10_1_GE21T
      REMOVE T10_1_NST
      REMOVE T10_1_TT
      REMOVE T10_2_SASM
      REMOVE T10_2_OTHM
      REMOVE T10_2_SASF
      REMOVE T10_2_OTHF
      REMOVE T10_2_SAST
      REMOVE T10_2_OTHT
      REMOVE T10_3_EDUM
      REMOVE T10_3_ARTM
      REMOVE T10_3_HUMM
      REMOVE T10_3_SOCM
      REMOVE T10_3_SCIM
      REMOVE T10_3_ENGM
      REMOVE T10_3_AGRM
      REMOVE T10_3_HEAM
      REMOVE T10_3_SERM
      REMOVE T10_3_OTHM
      REMOVE T10_3_NSM
      REMOVE T10_3_TM
      REMOVE T10_3_EDUF
      REMOVE T10_3_ARTF
      REMOVE T10_3_HUMF
      REMOVE T10_3_SOCF
      REMOVE T10_3_SCIF
      REMOVE T10_3_ENGF
      REMOVE T10_3_AGRF
      REMOVE T10_3_HEAF
      REMOVE T10_3_SERF
      REMOVE T10_3_OTHF
      REMOVE T10_3_NSF
      REMOVE T10_3_TF
      REMOVE T10_3_EDUT
      REMOVE T10_3_ARTT
      REMOVE T10_3_HUMT
      REMOVE T10_3_SOCT
      REMOVE T10_3_SCIT
      REMOVE T10_3_ENGT
      REMOVE T10_3_AGRT
      REMOVE T10_3_HEAT
      REMOVE T10_3_SERT
      REMOVE T10_3_OTHT
      REMOVE T10_3_NST
      REMOVE T10_3_TT
      REMOVE T10_4_NFM
      REMOVE T10_4_PM
      REMOVE T10_4_LSM
      REMOVE T10_4_USM
      REMOVE T10_4_TVM
      REMOVE T10_4_ACCAM
      REMOVE T10_4_HCM
      REMOVE T10_4_ODNDM
      REMOVE T10_4_HDPQM
      REMOVE T10_4_PDM
      REMOVE T10_4_DM
      REMOVE T10_4_NSM
      REMOVE T10_4_TM
      REMOVE T10_4_NFF
      REMOVE T10_4_PF
      REMOVE T10_4_LSF
      REMOVE T10_4_USF
      REMOVE T10_4_TVF
      REMOVE T10_4_ACCAF
      REMOVE T10_4_HCF
      REMOVE T10_4_ODNDF
      REMOVE T10_4_HDPQF
      REMOVE T10_4_PDF
      REMOVE T10_4_DF
      REMOVE T10_4_NSF
      REMOVE T10_4_TF
      REMOVE T10_4_NFT
      REMOVE T10_4_PT
      REMOVE T10_4_LST
      REMOVE T10_4_UST
      REMOVE T10_4_TVT
      REMOVE T10_4_ACCAT
      REMOVE T10_4_HCT
      REMOVE T10_4_ODNDT
      REMOVE T10_4_HDPQT
      REMOVE T10_4_PDT
      REMOVE T10_4_DT
      REMOVE T10_4_NST
      REMOVE T10_4_TT
      REMOVE T11_1_FW
      REMOVE T11_1_BIW
      REMOVE T11_1_BUW
      REMOVE T11_1_TDLW
      REMOVE T11_1_MW
      REMOVE T11_1_CDW
      REMOVE T11_1_CPW
      REMOVE T11_1_VW
      REMOVE T11_1_OTHW
      REMOVE T11_1_WMFHW
      REMOVE T11_1_NSW
      REMOVE T11_1_TW
      REMOVE T11_1_FS
      REMOVE T11_1_BIS
      REMOVE T11_1_BUS
      REMOVE T11_1_TDLS
      REMOVE T11_1_MS
      REMOVE T11_1_CDS
      REMOVE T11_1_CPS
      REMOVE T11_1_VS
      REMOVE T11_1_OTHS
      REMOVE T11_1_WMFHS
      REMOVE T11_1_NSS
      REMOVE T11_1_TS
      REMOVE T11_1_FT
      REMOVE T11_1_BIT
      REMOVE T11_1_BUT
      REMOVE T11_1_TDLT
      REMOVE T11_1_MT
      REMOVE T11_1_CDT
      REMOVE T11_1_CPT
      REMOVE T11_1_VT
      REMOVE T11_1_OTHT
      REMOVE T11_1_WMFHT
      REMOVE T11_1_NST
      REMOVE T11_1_TT
      REMOVE T11_2_T1
      REMOVE T11_2_T2
      REMOVE T11_2_T3
      REMOVE T11_2_T4
      REMOVE T11_2_T5
      REMOVE T11_2_T6
      REMOVE T11_2_T7
      REMOVE T11_2_T8
      REMOVE T11_2_NS
      REMOVE T11_2_T
      REMOVE T11_3_D1
      REMOVE T11_3_D2
      REMOVE T11_3_D3
      REMOVE T11_3_D4
      REMOVE T11_3_D5
      REMOVE T11_3_D6
      REMOVE T11_3_NS
      REMOVE T11_3_T
      REMOVE T12_1_M
      REMOVE T12_1_F
      REMOVE T12_1_T
      REMOVE T12_2_M
      REMOVE T12_2_F
      REMOVE T12_2_T
      REMOVE T12_3_VGM
      REMOVE T12_3_VGF
      REMOVE T12_3_VGT
      REMOVE T12_3_GM
      REMOVE T12_3_GF
      REMOVE T12_3_GT
      REMOVE T12_3_FM
      REMOVE T12_3_FF
      REMOVE T12_3_FT
      REMOVE T12_3_BM
      REMOVE T12_3_BF
      REMOVE T12_3_BT
      REMOVE T12_3_VBM
      REMOVE T12_3_VBF
      REMOVE T12_3_VBT
      REMOVE T12_3_NSM
      REMOVE T12_3_NSF
      REMOVE T12_3_NST
      REMOVE T12_3_TM
      REMOVE T12_3_TF
      REMOVE T12_3_TT
      REMOVE T13_1_MDSOM
      REMOVE T13_1_POM
      REMOVE T13_1_APTOM
      REMOVE T13_1_ASOM
      REMOVE T13_1_STOM
      REMOVE T13_1_CLOSOM
      REMOVE T13_1_SCSOM
      REMOVE T13_1_PPMOM
      REMOVE T13_1_EOM
      REMOVE T13_1_NSM
      REMOVE T13_1_TM
      REMOVE T13_1_MDSOF
      REMOVE T13_1_POF
      REMOVE T13_1_APTOF
      REMOVE T13_1_ASOF
      REMOVE T13_1_STOF
      REMOVE T13_1_CLOSOF
      REMOVE T13_1_SCSOF
      REMOVE T13_1_PPMOF
      REMOVE T13_1_EOF
      REMOVE T13_1_NSF
      REMOVE T13_1_TF
      REMOVE T13_1_MDSOT
      REMOVE T13_1_POT
      REMOVE T13_1_APTOT
      REMOVE T13_1_ASOT
      REMOVE T13_1_STOT
      REMOVE T13_1_CLOSOT
      REMOVE T13_1_SCSOT
      REMOVE T13_1_PPMOT
      REMOVE T13_1_EOT
      REMOVE T13_1_NST
      REMOVE T13_1_TT
      REMOVE T14_1_AFFM
      REMOVE T14_1_BCM
      REMOVE T14_1_MIM
      REMOVE T14_1_CTM
      REMOVE T14_1_TCM
      REMOVE T14_1_PAM
      REMOVE T14_1_PSM
      REMOVE T14_1_OTHM
      REMOVE T14_1_TM
      REMOVE T14_1_AFFF
      REMOVE T14_1_BCF
      REMOVE T14_1_MIF
      REMOVE T14_1_CTF
      REMOVE T14_1_TCF
      REMOVE T14_1_PAF
      REMOVE T14_1_PSF
      REMOVE T14_1_OTHF
      REMOVE T14_1_TF
      REMOVE T14_1_AFFT
      REMOVE T14_1_BCT
      REMOVE T14_1_MIT
      REMOVE T14_1_CTT
      REMOVE T14_1_TCT
      REMOVE T14_1_PAT
      REMOVE T14_1_PST
      REMOVE T14_1_OTHT
      REMOVE T14_1_TT
      REMOVE T15_1_NC
      REMOVE T15_1_1C
      REMOVE T15_1_2C
      REMOVE T15_1_3C
      REMOVE T15_1_GE4C
      REMOVE T15_1_NSC
      REMOVE T15_1_TC
      REMOVE T15_2_Y
      REMOVE T15_2_N
      REMOVE T15_2_NS
      REMOVE T15_2_T
      REMOVE T15_3_B
      REMOVE T15_3_OTH
      REMOVE T15_3_N
      REMOVE T15_3_NS
      REMOVE T15_3_T
      RENAME_SET_VALUE _area > AREA_SQMET
      RENAME_SET_VALUE Pop_Density > POP_DENS
      RENAME_SET_VALUE Dep_Ratio > DEP_RATIO
      RENAME_SET_VALUE Percent_NonIrish > PER_NONIRE
      RENAME_SET_VALUE HouseBuilt_Pre2001 > HO_PRE2001
      RENAME_SET_VALUE HouseBuilt_Post2001 > HO_POS2001
      RENAME_SET_VALUE Percent_FlatApartBedsit > PER_FLAPBE
      RENAME_SET_VALUE Percent_Rented > PER_RENT
      RENAME_SET_VALUE Percent_Vacant > PER_VAC
      RENAME_SET_VALUE Percent_Unemployed > PER_UNEM
      RENAME_SET_VALUE Percent_Professional > PER_PROF
      RENAME_SET_VALUE Percent_OtherOccupation > PER_O_OCC
      RENAME_SET_VALUE Percent_ThirdLevelEdu > PER_3ED
      RENAME_SET_VALUE Percent_NoThirdLevelEdu > PER_NO3ED
      RENAME_SET_VALUE Average_PersonsPerHousehold > AV_PER_HOU
      RENAME_SET_VALUE Percent_NoInternet > PER_NO_INT
      RENAME_SET_VALUE Percent_WithDisability > PER_DISAB
      RENAME_SET_VALUE TotalPop2011 > TO_POP2011
      RENAME_SET_VALUE Percent_ChangePopulation > PER_CH_POP
      RENAME_SET_VALUE TotalHouse2011 > TO_HOU2011
      RENAME_SET_VALUE Percent_ChangeHouseholds > PER_CH_HOU
    -> SAPS_2016 (writer CSV2_11)
    -> SAPS_2016 (writer JSON_1)
    -> SAPS_2016 (writer ESRISHAPE_9)
    -> AttributeManager_2

Bookmark: Attribute Display Names
AttributeManager_2
    ATTR_TABLE:
      SET_TO GUID = Globally Unique Identifier
      SET_TO NUTS1 = NUTS 1 Region ID
      SET_TO NUTS1NAME = NUTS 1 Region Name
      SET_TO NUTS2 = NUTS 2 Region ID
      SET_TO NUTS2NAME = NUTS 2 Region Name
      SET_TO NUTS3 = NUTS 3 Region ID
      SET_TO NUTS3NAME = NUTS 3 Region Name
      SET_TO COUNTY = County ID
      SET_TO COUNTYNAME = County Name
      SET_TO CSOED = CSO Electoral District ID
      SET_TO OSIED = OSI Electoral District ID
      SET_TO EDNAME = Electoral District Name
      SET_TO SA_PUB2011 = Small Area ID 2011
      SET_TO SMALL_AREA = Small Area ID 2016
      SET_TO GEOGID = Geographic ID
      SET_TO GEOGDESC = Geographic Description
      SET_TO TO_POP2016 = Total Population 2016
      SET_TO TO_HOU2016 = Total Number of Households 2016
      SET_TO AREA_SQMET = Area (km sq)
      SET_TO POP_DENS = Population Density (per km sq)
      SET_TO DEP_RATIO = Dependency Ratio (per 100)
      SET_TO PER_NONIRE = Percentage of Non-Irish Nationals
      SET_TO HO_PRE2001 = Households Built to 2000
      SET_TO HO_POS2001 = Housholds Built 2001 to 2016
      SET_TO PER_FLAPBE = Percentage of Households in Flats/Apartments/Bedsits
      SET_TO PER_RENT = Percentage of Rented Households
      SET_TO PER_VAC = Percentage of Vacant Households (excluding holiday homes)
      SET_TO PER_UNEM = Percentage of Unemployed Persons
      SET_TO PER_PROF = Percentage of Population in Professional, Management and Technical Class (A & B)
      SET_TO PER_O_OCC = Percentage of Population Other Class Bands (C-Z)
      SET_TO PER_3ED = Percentage of Population With 3rd Level Education
      SET_TO PER_NO3ED = Percentage of Population Without 3rd Level Education
      SET_TO AV_PER_HOU = Average Number of Persons Per Household
      SET_TO PER_NO_INT = Percentage of Households Without Internet
      SET_TO PER_DISAB = Percentage of Persons with a Disability
      SET_TO TO_POP2011 = Total Population 2011
      SET_TO PER_CH_POP = Percentage Change of Total Population 2011-2016
      SET_TO TO_HOU2011 = Total Number of Households 2016
      SET_TO PER_CH_HOU = Percentage Change of Total Housholds 2011-2016
    -> DuplicateFilter_4
DuplicateFilter_4
    INPUT_ORDERED_CHOICE = Yes
    KEYATTR = CSOED PER_UNEM OSIED AV_PER_HOU AREA_SQMET EDNAME NUTS1 NUTS3 PER_VAC NUTS1NAME NUTS2NAME POP_DENS TO_POP2016 GUID SA_PUB2011 GEOGID NUTS3NAME TO_POP2011 DEP_RATIO PER_NO_INT HO_POS2001 COUNTYNAME PER_DISAB PER_NONIRE PER_RENT PER_NO3ED TO_HOU2016 PER_CH_HOU GEOGDESC NUTS2 SMALL_AREA PER_3ED PER_CH_POP PER_FLAPBE PER_O_OCC COUNTY PER_PROF HO_PRE2001 TO_HOU2011
    UNIQUE -> AttributeExploder
AttributeExploder
    ATTR_NAME_LABEL = _attr_name
    ATTR_VALUE_LABEL = _attr_value
    EXPLODING_TYPE = Features
    KEEP_ATTRIBUTES = Yes
    KEEP_GEOMETRY = No
    -> Tester
Tester
    BOOL_OP = OR
    COMPOSITE_TEST = 1 OR 2 OR 3 OR 4
    TEST_CLAUSE:
      CASE_INSENSITIVE_TEST @Value(_attr_name) BEGINS_WITH fme_
      CASE_INSENSITIVE_TEST @Value(_attr_name) BEGINS_WITH multi_reader_
      CASE_INSENSITIVE_TEST @Value(_attr_name) BEGINS_WITH __fme
      CASE_INSENSITIVE_TEST @Value(_attr_name) BEGINS_WITH csv_
    TEST_MODE = CASE_INSENSITIVE_TEST
    FAILED -> Sorter_4
Sorter_4
    SORT_PARM = _attr_name ALPHA ASCENDING
    SORTED -> AttributeManager_3
AttributeManager_3
    ATTR_TABLE:
      REMOVE GUID
      REMOVE NUTS1
      REMOVE NUTS1NAME
      REMOVE NUTS2
      REMOVE NUTS2NAME
      REMOVE NUTS3
      REMOVE NUTS3NAME
      REMOVE COUNTY
      REMOVE COUNTYNAME
      REMOVE CSOED
      REMOVE OSIED
      REMOVE EDNAME
      REMOVE SA_PUB2011
      REMOVE SMALL_AREA
      REMOVE GEOGID
      REMOVE GEOGDESC
      REMOVE TO_POP2016
      REMOVE TO_HOU2016
      REMOVE AREA_SQMET
      REMOVE POP_DENS
      REMOVE DEP_RATIO
      REMOVE PER_NONIRE
      REMOVE HO_PRE2001
      REMOVE HO_POS2001
      REMOVE PER_FLAPBE
      REMOVE PER_RENT
      REMOVE PER_VAC
      REMOVE PER_UNEM
      REMOVE PER_PROF
      REMOVE PER_O_OCC
      REMOVE PER_3ED
      REMOVE PER_NO3ED
      REMOVE AV_PER_HOU
      REMOVE PER_NO_INT
      REMOVE PER_DISAB
      REMOVE TO_POP2011
      REMOVE PER_CH_POP
      REMOVE TO_HOU2011
      REMOVE PER_CH_HOU
      RENAME_SET_VALUE _attr_name > Attribute_Name
      RENAME_SET_VALUE _attr_value > Display_Name
    -> SAPS_2016_Attribute_Names (writer CSV2_13)

Bookmark: Geolocated Property Price Register (Dublin / 2019)
Note: Data Source: / https://propertypriceregister.ie/ / File: / PPR_2016Q1_2019Q1_All.shp / NOTE: Property Price Data have been geolocated by AIRO
PPR_2016Q1_2019Q1_All (reader ESRISHAPE_7)
    attributes: OBJECTID long, AiroID long, Address char(254), Postal_Cod char(254), County char(254), Date_of_Sa date, Price double, Not_Full_M char(254), VAT_Exclus char(254), PropertyTy char(254), PropertyDe char(254), ING_East double, ING_North double, Match_leve char(254), Year long, Month long, Qtr char(254), Quarter char(254)
    -> Reprojector_5

Bookmark: Reproject Data
Note: Reprojector Parameters: / 1. Destination Coordinate System = EPSG:2157
Reprojector_5
    DEST = EPSG:2157
    INTERPOLATION_TYPE_NAME = Nearest Neighbor
    RASTER_CELL_SIZE = Preserve Cells
    RASTER_TOLERANCE = 0.0
    SOURCE = Read from feature
    REPROJECTED -> Clipper_7 [CLIPPEE]

Bookmark: Clip spatial data to boundary
Note: Clipper Parameters: / 1. Clippees on Clipper Boundary = Treat as Inside
Clipper_7
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> CoordinateExtractor_3

Bookmark: Extract Coordinates
Note: Coordiante Extractor Parameters: / 1. Mode = Specify Coordinate / 2. X Attribute = _x / 3. Y Attribute = _y / 4. Z Attribute = _z
CoordinateExtractor_3
    IND = 0
    MODE = Specify Coordinate
    X_ATTR = _x
    Y_ATTR = _y
    Z_ATTR = _z
    Z_DEFAULT = 0
    -> FeatureMerger_3 [REQUESTOR]

Bookmark: 3D Marker
Note: Data Source: / Custom Model / Note: Model pivot placed at base
marker_blue (reader OBJ_1)
    -> 3DRotator

Bookmark: 3D Model Preparation
Note: 3D Rotator Parameters: / Angle in Degrees = 90 / Rotate Along = X Axis
3DRotator
    ANGLE = 90
    AXIS_CHOICE = X Axis
    ROTATED -> GeometryExtractor
Note: 3D Rotator Parameters: / Angle in Degrees = 90 / Rotate Along = X Axis
GeometryExtractor
    ATTR = _geometry
    ELLIPSOID_NAME = WGS84
    GEOHASH_PRECISION_DISPLAY = ~9.3 mm (12 characters)
    ISO6709_FORMAT_CHOICE = Degrees and Decimal Degrees
    ISO6709_MAX_DECIMAL_PLACES = 5
    JSON_MAX_DIGITS = 7
    KIND_LONG = FME Binary
    LETTERING = WGS84
    LEVELS_ATTR = _levels
    MSSQL_FORMAT_CHOICE = Geometry
    OGCVERSION = 1.2
    OGC_WKT_PRECISION_DISPLAY = 64-bit
    OGEOSMS_URL_PREFIX = http://maps.google.com/?q=
    OMIT_NAMESPACES_DISPLAY = No
    PRECISION = 0
    PREFER_POLYGON_OVER_SURFACE = No
    REMOVE_GEOMETRY = No
    -> FeatureMerger_2 [SUPPLIER]
    -> FeatureMerger [SUPPLIER]
    -> FeatureMerger_3 [SUPPLIER]

Bookmark: Data Processing
Note: Feature Joiner Parameters: / 1.Join On = 1/1 [Unconditional Match) / 2. Feature Merge Type = Geometry and Attributes
FeatureMerger_3
    ATTR_ACCUM_MODE = Merge Supplier
    ATTR_CONFLICT_RES = Use Requestor
    IGNORE_NULLS = No
    JOIN_KEYS = 1 1 AUTO
    MERGE_TYPE = Attributes and Geometry
    PROCESS_DUPS = NO
    REJECT_NULL_MISSING_KEYS = No
    SUPPLIERS_FIRST = No
    MERGED -> GeometryPropertySetter_6
Note: Geometry Property Setter Parameters: / 1. Property to Set = Geometry Name / 2. Geometry Name = OBJECTID
GeometryPropertySetter_6
    GEOM_NAME_FIELD = @Value(OBJECTID)
    OVERWRITE_CHOICE = Yes
    SETTYPE_PARAM = Geometry Name
    SET -> Offsetter_3

Bookmark: Align 3D markers to geographic coordinates
Note: Offsetter Parameters: / 1. Mode = Cartesian Coordinates / 2. X Offset = _x / 3. Y Offset = _y / 4. Z Offset = _z
Offsetter_3
    MODE = Cartesian Coordinate
    XOFF = @Value(_x)
    YOFF = @Value(_y)
    ZOFF = @Value(_z)
    OFFSET -> Reprojector_6
Note: Reprojector Parameters: / 1.Destination Coordinate System = EPSG:2157
Reprojector_6
    DEST = EPSG:2157
    INTERPOLATION_TYPE_NAME = Nearest Neighbor
    RASTER_CELL_SIZE = Preserve Cells
    RASTER_TOLERANCE = 0.0
    SOURCE = Read from feature
    REPROJECTED -> Inspector_6
    REPROJECTED -> Price_Paid_Register (writer FBX_5)
    REPROJECTED -> Price_Paid_Register (writer CSV2_7)

Bookmark: File Outputs
Inspector_6
Note: FBX Writer Parameters: / 1. SET OUTPUT FILE LOCATION / 2. Coordinate System = EPSG:2157 / 3. Move to Local Coordinate System = No
Price_Paid_Register (writer FBX_5)
Note: CSV Writer Parameters: / 1. SET OUTPUT FILE LOCATION
Price_Paid_Register (writer CSV2_7)
    attributes: OBJECTID string, AiroID string, Address string, Postal_Cod string, County string, Date_of_Sa string, Price string, Not_Full_M string, VAT_Exclus string, PropertyTy string, PropertyDe string, ING_East string, ING_North string, Match_leve string, Year string, Month string, Qtr string, Quarter string

Bookmark: National Monuments Dataset
Note: Data Source: / http://webgis.archaeology.ie/historicenvironment/ / File: / NIAH_Sites.shp
National_Monuments (reader ESRISHAPE_6)
    attributes: ENTITY_ID char(7), CLASSCODE char(4), NAT_GRID_E double, NAT_GRID_N double, RMP_PROP short, CO_ID long, ITM_E double, ITM_N double, CLASSDESC char(60), SMRS char(100), TLAND_NAME char(254)
    -> Clipper_4 [CLIPPEE]

Bookmark: Clip spatial data to boundary
Note: Clipper Parameters: / 1. Clippees on Clipper Boundary = Treat as Inside
Clipper_4
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> CoordinateExtractor_2

Bookmark: Extract Coordinates
Note: Coordiante Extractor Parameters: / 1. Mode = Specify Coordinate / 2. X Attribute = _x / 3. Y Attribute = _y / 4. Z Attribute = _z
CoordinateExtractor_2
    IND = 0
    MODE = Specify Coordinate
    X_ATTR = _x
    Y_ATTR = _y
    Z_ATTR = _z
    Z_DEFAULT = 0
    -> FeatureMerger [REQUESTOR]

Bookmark: Data Processing
Note: Feature Joiner Parameters: / 1.Join On = 1/1 [Unconditional Match) / 2. Feature Merge Type = Geometry and Attributes
FeatureMerger
    ATTR_ACCUM_MODE = Merge Supplier
    ATTR_CONFLICT_RES = Use Requestor
    IGNORE_NULLS = No
    JOIN_KEYS = 1 1 AUTO
    MERGE_TYPE = Attributes and Geometry
    PROCESS_DUPS = NO
    REJECT_NULL_MISSING_KEYS = No
    SUPPLIERS_FIRST = No
    MERGED -> GeometryPropertySetter_4
Note: Geometry Property Setter Parameters: / 1. Property to Set = Geometry Name / 2. Geometry Name = ENTITY_ID
GeometryPropertySetter_4
    GEOM_NAME_FIELD = @Value(ENTITY_ID)
    OVERWRITE_CHOICE = Yes
    SETTYPE_PARAM = Geometry Name
    SET -> Offsetter

Bookmark: Align 3D markers to geographic coordinates
Note: Offsetter Parameters: / 1. Mode = Cartesian Coordinates / 2. X Offset = _x / 3. Y Offset = _y / 4. Z Offset = _z
Offsetter
    MODE = Cartesian Coordinate
    XOFF = @Value(_x)
    YOFF = @Value(_y)
    ZOFF = @Value(_z)
    OFFSET -> Reprojector_3
Note: Reprojector Parameters: / 1.Destination Coordinate System = EPSG:2157
Reprojector_3
    DEST = EPSG:2157
    INTERPOLATION_TYPE_NAME = Nearest Neighbor
    RASTER_CELL_SIZE = Preserve Cells
    RASTER_TOLERANCE = 0.0
    SOURCE = Read from feature
    REPROJECTED -> Inspector_4
    REPROJECTED -> National_Monuments (writer FBX_4)
    REPROJECTED -> National_Monuments (writer CSV2_6)

Bookmark: File Outputs
Inspector_4
Note: FBX Writer Parameters: / 1. SET OUTPUT FILE LOCATION / 2. Coordinate System = EPSG:2157 / 3. Move to Local Coordinate System = No
National_Monuments (writer FBX_4)
Note: CSV Writer Parameters: / 1. SET OUTPUT FILE LOCATION
National_Monuments (writer CSV2_6)
    attributes: ENTITY_ID string, CLASSCODE string, NAT_GRID_E string, NAT_GRID_N string, RMP_PROP string, CO_ID string, ITM_E string, ITM_N string, CLASSDESC string, SMRS string, TLAND_NAME string

Bookmark: National Inventory of Architectural Heritage Dataset
Note: Data Source: / http://webgis.archaeology.ie/historicenvironment/ / File: / NIAH_Sites.shp
NIAH_Sites (reader ESRISHAPE_5)
    attributes: REG_NO long, SURVEY_ID char(50), created_us char(254), created_da date, last_edite char(254), last_edi_1 date, PUBLISH long, DATE char(20), NAME char(100), NUMBER char(50), STREET1 char(50), STREET2 char(50), TLAND_NAME char(254), TOWN char(50), COUNTY_COD char(50), COUNTY char(15), LOCAL_AUTH char(63), RPS long, RMP long, VALUE_DESC char(50), ORIGINALTY char(254), INUSETYPE char(254), NIAH_SITE_ char(87)
    -> Clipper_5 [CLIPPEE]

Bookmark: Clip spatial data to boundary
Note: Clipper Parameters: / 1. Clippees on Clipper Boundary = Treat as Inside
Clipper_5
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> CoordinateExtractor

Bookmark: Extract Coordinates
Note: Coordiante Extractor Parameters: / 1. Mode = Specify Coordinate / 2. X Attribute = _x / 3. Y Attribute = _y / 4. Z Attribute = _z
CoordinateExtractor
    IND = 0
    MODE = Specify Coordinate
    X_ATTR = _x
    Y_ATTR = _y
    Z_ATTR = _z
    Z_DEFAULT = 0
    -> FeatureMerger_2 [REQUESTOR]

Bookmark: Data Processing
Note: Feature Joiner Parameters: / 1.Join On = 1/1 [Unconditional Match) / 2. Feature Merge Type = Geometry and Attributes
FeatureMerger_2
    ATTR_ACCUM_MODE = Merge Supplier
    ATTR_CONFLICT_RES = Use Requestor
    IGNORE_NULLS = No
    JOIN_KEYS = 1 1 AUTO
    MERGE_TYPE = Attributes and Geometry
    PROCESS_DUPS = NO
    REJECT_NULL_MISSING_KEYS = No
    SUPPLIERS_FIRST = No
    MERGED -> GeometryPropertySetter_5
Note: Geometry Property Setter Parameters: / 1. Property to Set = Geometry Name / 2. Geometry Name = REG_NO
GeometryPropertySetter_5
    GEOM_NAME_FIELD = @Value(REG_NO)
    OVERWRITE_CHOICE = Yes
    SETTYPE_PARAM = Geometry Name
    SET -> Offsetter_2

Bookmark: Align 3D markers to geographic coordinates
Note: Offsetter Parameters: / 1. Mode = Cartesian Coordinates / 2. X Offset = _x / 3. Y Offset = _y / 4. Z Offset = _z
Offsetter_2
    MODE = Cartesian Coordinate
    XOFF = @Value(_x)
    YOFF = @Value(_y)
    ZOFF = @Value(_z)
    OFFSET -> Reprojector_4
Note: Reprojector Parameters: / 1.Destination Coordinate System = EPSG:2157
Reprojector_4
    DEST = EPSG:2157
    INTERPOLATION_TYPE_NAME = Nearest Neighbor
    RASTER_CELL_SIZE = Preserve Cells
    RASTER_TOLERANCE = 0.0
    SOURCE = Read from feature
    REPROJECTED -> Inspector_7
    REPROJECTED -> NIAH_Sites (writer FBX_6)
    REPROJECTED -> NIAH_Sites (writer CSV2_8)

Bookmark: File Outputs
Inspector_7
Note: FBX Writer Parameters: / 1. SET OUTPUT FILE LOCATION / 2. Coordinate System = EPSG:2157 / 3. Move to Local Coordinate System = No
NIAH_Sites (writer FBX_6)
Note: CSV Writer Parameters: / 1. SET OUTPUT FILE LOCATION
NIAH_Sites (writer CSV2_8)
    attributes: REG_NO string, SURVEY_ID string, created_us string, created_da string, last_edite string, last_edi_1 string, PUBLISH string, DATE string, NAME string, NUMBER string, STREET1 string, STREET2 string, TLAND_NAME string, TOWN string, COUNTY_COD string, COUNTY string, LOCAL_AUTH string, RPS string, RMP string, VALUE_DESC string, ORIGINALTY string, INUSETYPE string, NIAH_SITE_ string

Bookmark: Dublin Planning Applications
Note: Known Issues: / 1. Input Shapefile had to be reprojected outside of FME as it was using a deprecated Coordinate System. / 2. Workaround to address issue where shapefile polygons are split in to through clipping. / NOTE: Output FBX has overlapping meshes representing planning applications for the same or similar spatial extents at different times.

Bookmark: Dublin Development Plan
Note: Known Issues: / 1. Input CSV is manually cleaned from original XLSX. / 2.Workaround to address issue where shapefile polygons are split in to through clipping.

Bookmark: Small Area Population Statistics
Note: Known Issues: / 1. Workaround to address issue where shapefile polygons are split in to through clipping. / 2. Calculated figures have been rounded to 2 decimal places for display. This mitigates some rounding errors but others could arise necessitating greater precision. / 3. This workspace currently assumes that all 2016 boundaries match those from 2011.
