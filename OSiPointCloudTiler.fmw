FME workspace OSiPointCloudTiler.fmw

Parameters:
- SourceDataset_ESRISHAPE = D:\BCD_Data\2019_12_11_Print_Tiles_Dublin_Boundary_7x4km_1-2000_1km\Print Tiles Dublin Boundary 7x4km 1-2000 1km Tile.shp   # Source Esri Shapefile(s)
- SourceDataset_LAS = D:\BCD_OSi_Point_Cloud_Data\Dublin\LiDAR_2009_Hackathon_Dublin_2m_DTM.xyz.las   # Source ASPRS LAS File(s)
- SourceDataset_LAS_3 = ""D:\BCD_OSi_Point_Cloud_Data\Dublin\RAWDSM\a_FCIR_20170408_110916.las" "D:\BCD_OSi_Point_Cloud_Data\Dublin\RAWDSM\a_FCIR_20170408_112657.las" "D:\BCD_OSi_Point_Cloud_Data\Dublin\RAWDSM\a_FCIR_20170408_141111.las" "D:\BCD_OSi_Point_Cloud_Data\Dublin\RAWDSM\a_FCIR_20170408_142635.las" "D:\BCD_OSi_Point_Cloud_Data\Dublin\RAWDSM\a_FCIR_20170408_144524.las" "D:\BCD_OSi_Point_Cloud_Data\Dublin\RAWDSM\b_FCIR_20170408_110916.las" "D:\BCD_OSi_Point_Cloud_Data\Dublin\RAWDSM\b_FCIR_20170408_112657.las" "D:\BCD_OSi_Point_Cloud_Data\Dublin\RAWDSM\b_FCIR_20170408_141111.las" "D:\BCD_OSi_Point_Cloud_Data\Dublin\RAWDSM\b_FCIR_20170408_142635.las" "D:\BCD_OSi_Point_Cloud_Data\Dublin\RAWDSM\b_FCIR_20170408_144524.las" "D:\BCD_OSi_Point_Cloud_Data\Dublin\RAWDSM\c_FCIR_20170408_110916.las" "D:\BCD_OSi_Point_Cloud_Data\Dublin\RAWDSM\c_FCIR_20170408_112657.las" "D:\BCD_OSi_Point_Cloud_Data\Dublin\RAWDSM\c_FCIR_20170408_141111.las" "D:\BCD_OSi_Point_Cloud_Data\Dublin\RAWDSM\c_FCIR_20170408_142635.las" "D:\BCD_OSi_Point_Cloud_Data\Dublin\RAWDSM\c_FCIR_20170408_144524.las""   # Source ASPRS LAS File(s)
- DestDataset_LAS = D:\OSi_Dublin_3D_Model\Tiled_Pointclouds\Dublin_DSM   # Destination ASPRS LAS Folder
- DestDataset_LAS_2 = D:\OSi_Dublin_3D_Model\Tiled_Pointclouds\Dublin_DTM   # Destination ASPRS LAS Folder

Readers:
- ESRISHAPE_1: ESRISHAPE from $(SourceDataset_ESRISHAPE)
- LAS_1: LAS from $(SourceDataset_LAS)
- LAS_2: LAS from $(SourceDataset_LAS_3)

Writers:
- LAS_3: LAS to $(DestDataset_LAS) in EPSG:2157
- LAS_4: LAS to $(DestDataset_LAS_2) in EPSG:2157

Bookmark: Dublin Tiles
Print Tiles Dublin Boundary 7x4km 1-2000 1km Tile (reader ESRISHAPE_1)
    attributes: left double, top double, right double, bottom double, id long
    -> Clipper [CLIPPER]
    -> Clipper_2 [CLIPPER]

Bookmark: Dublin DSM
LAS (reader LAS_2)
    -> Clipper [CLIPPEE]

Bookmark: DSM Clipper
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> PointCloudCombiner

Bookmark: Combine Points by Tile ID
PointCloudCombiner
    ACCUM_ATTRS_NAME = Yes
    EXTRACT_RASTER_NODATA_NAME = No
    GROUP_BY = id
    SPACING = 1.0
    -> LAS (writer LAS_3)

Bookmark: Tiled Dublin DSM
LAS (writer LAS_3)

Bookmark: Dublin DTM
LAS (reader LAS_1)
    -> Clipper_2 [CLIPPEE]

Bookmark: DTM Clipper
Clipper_2
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    LINES_AS_SEGMENTS = No
    MEASURE_TYPE = Continuous
    MISSING_VAL_MODE = Compute
    PRESERVE_CLIPPEE_EXTENTS = No
    VAL_SOURCE = Clippee Only
    INSIDE -> PointCloudCombiner_2

Bookmark: CombinePoints by Tile ID
PointCloudCombiner_2
    ACCUM_ATTRS_NAME = Yes
    EXTRACT_RASTER_NODATA_NAME = No
    GROUP_BY = id
    SPACING = 1.0
    -> LAS (writer LAS_4)

Bookmark: Tiled Dublin DTM
LAS (writer LAS_4)
